FME workspace makeMultipleKnr.fmw

Parameters:
- knr_list = 1826,1820,5403,3428,4631,1871,3012,4203,3025,4645,4627,1547,1576,4641,3026,4625,4632,1554,5422,3813,5416,1839,4601,5440,1811,4216,1114,4624,1804,1145,4648,1813,4220,4222,3024,1867,4613,5443,5441,3431,3005,3815,5420,1827,4619,3416,3035,1101,3420,3028,3425,4611,3450,1853,4219,4206,1841,4633,4615,4646,1578,1859,5049,4207,3050,3039,3429,3004,3022,4214,5036,5014,3823,3811,5426,5439,3441,1838,1532,1557,3032,4211,1122,3407,4650,3041,3446,1825,5414,4202,5045,3417,4635,5430,1866,3001,3403,1875,5406,1517,5402,5433,1106,5055,1832,3042,1515,1818,5056,3819,1133,3044,3038,3802,5026,3801,3037,1579,3011,4637,4226,4638,5046,1119,5413,5053,5054,3014,4218,3053,5437,5423,1149,4602,1120,3006,3401,3814,4204,1505,3046,4622,4227,4617,3821,1144,5411,5429,3805,5438,1822,5052,3432,5037,3049,5042,3405,4215,3030,4205,5415,3434,5432,1112,3054,1834,4644,4225,5424,4642,1851,3029,3412,5031,3013,4634,5028,1837,5034,5027,3817,4629,3047,1506,1874,3002,5418,5434,5007,5044,3036,1806,3034,3040,1828,3023,3822,3031,3816,3451,3436,5435,3414,3020,3448,5428,3052,3808,5060,5021,5059,3430,5020,0301,4630,5047,5436,3806,5043,3016,1833,1127,1539,3424,5022,5061,3439,3007,3411,4201,3051,3027,1836,5025,1856,3017,5417,1840,4623,1514,3804,1108,3003,1135,3437,5032,3820,5421,3045,3812,4228,5029,3807,3015,5427,3433,1573,5041,4640,1111,1124,4636,1870,4649,3413,1103,1848,5006,5035,4614,3423,5425,1130,1525,4651,1531,1134,1563,4647,1566,4612,1528,1812,3447,3449,1845,3438,3415,5419,5444,1121,1560,3818,5412,3824,3426,5401,5001,3421,1835,4213,5033,3427,4616,1146,3803,3033,4618,1516,4620,5442,1151,5405,4628,4221,3454,1511,5404,1824,1815,4212,4223,5038,3019,1535,3452,3443,1860,1816,4639,1160,3825,1577,4621,1857,1865,3435,3419,3018,1868,5057,1520,3442,3048,3440,4626,3453,5058,3043,1507,4217,3422,4643,3021,4224,3418   # kommunenummer komma-separert

Creator
    GEOMTYPE = Geometry Object
    NUM = 1
    CREATED -> AttributeCreator
AttributeCreator
    ATTR_TABLE = SET_TO knr_liste = $(knr_list)
    -> AttributeSplitter
AttributeSplitter
    ATTR_NAME = knr_liste
    DELIMITER = ,
    DROP_EMPTY_PARTS = No
    LIST_NAME = knr
    TRIM_OPTION = Both
    -> ListExploder
ListExploder
    ATTR_ACCUM_MODE = Merge List Attributes
    ATTR_CONFLICT_RES = Use List Attribute Values
    INDEX_ATTR = _element_index
    LIST_ATTR = knr{}
    ELEMENTS -> WorkspaceRunner
WorkspaceRunner
    BLOCKING = No
    MAX_PROC = 7
    MAX_TO_BATCH = 1
    WORKSPACE_FILE = $(FME_MF_DIR)nvdbapi2gml_V3.fmw
    WORKSPACE_PARAMETERS = kommune,@Value(knr),mainFolder,C:\DATA\GIT\SOSI-Vegnett
