FME workspace makeGmlAndSosi.fmw

Parameters:
- kommune =   # kommunenummer

Creator
    GEOMTYPE = Geometry Object
    NUM = 1
    CREATED -> WorkspaceRunner
WorkspaceRunner
    BLOCKING = Yes
    WORKSPACE_FILE = $(FME_MF_DIR)nvdbapi2gml_V3.fmw
    WORKSPACE_PARAMETERS = kommune,$(kommune),mainFolder,C:\DATA\GIT\SOSI-Vegnett
    SUCCEEDED -> WorkspaceRunner_2
WorkspaceRunner_2
    BLOCKING = No
    MAX_TO_BATCH = 1
    WORKSPACE_FILE = $(FME_MF_DIR)gml2gdmmappersosi.fmw
    WORKSPACE_PARAMETERS = kommune,$(kommune),mainFolder,C:\DATA\GIT\SOSI-Vegnett
