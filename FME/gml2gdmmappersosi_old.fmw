FME workspace gml2gdmmappersosi_old.fmw

Parameters:
- kommune = 403   # Kommune
- mainFolder = C:\DATA\GitHub\NVDBGML\GML   # Hovedmappe
- fullFolder:   # Python Script
      fldr = FME_MacroValues['mainFolder'] + '\\kommune\\' + FME_MacroValues['kommune'] + '\\fkbvn'
      return fldr

Readers:
- GML_1: GML from $(fullFolder)\*.gml

Writers:
- GDMMAPPERSOSI_1: GDMMAPPERSOSI to $(fullFolder) in ETRS89.UTM-33N

Vegsperring (reader GML_1)
    attributes: identifikasjon.Identifikasjon.lokalId xml_buffer, identifikasjon.Identifikasjon.navnerom xml_buffer, identifikasjon.Identifikasjon.versjonId xml_buffer, endringsflagg.Endringsflagg.typeEndring xml_buffer, type xml_buffer, posisjon xml_geometry, lineærPosisjon.LineærPosisjonPunkt.lineærReferanseMetode xml_buffer, lineærPosisjon.LineærPosisjonPunkt.lenkesekvens.Identifikasjon.lokalId xml_buffer, lineærPosisjon.LineærPosisjonPunkt.lenkesekvens.Identifikasjon.navnerom xml_buffer, lineærPosisjon.LineærPosisjonPunkt.lenkesekvens.Identifikasjon.versjonId xml_buffer, lineærPosisjon.LineærPosisjonPunkt.posisjon xml_real64
    -> ListExploder
VærutsattVeg (reader GML_1)
    attributes: identifikasjon.Identifikasjon.lokalId xml_buffer, identifikasjon.Identifikasjon.navnerom xml_buffer, identifikasjon.Identifikasjon.versjonId xml_buffer, endringsflagg.Endringsflagg.typeEndring xml_buffer, høyfjellsstrekning xml_buffer, vinterstengt_FraDato xml_buffer, vinterstengt_TilDato xml_buffer, hovedproblem xml_buffer, senterlinje xml_geometry, lineærPosisjon{}.LineærPosisjonStrekning.lenkesekvens.Identifikasjon.lokalId xml_buffer, lineærPosisjon{}.LineærPosisjonStrekning.lenkesekvens.Identifikasjon.navnerom xml_buffer, lineærPosisjon{}.LineærPosisjonStrekning.lenkesekvens.Identifikasjon.versjonId xml_buffer, lineærPosisjon{}.LineærPosisjonStrekning.lineærReferanseMetode xml_buffer, lineærPosisjon{}.LineærPosisjonStrekning.retning xml_buffer, lineærPosisjon{}.LineærPosisjonStrekning.fraPosisjon xml_real64, lineærPosisjon{}.LineærPosisjonStrekning.tilPosisjon xml_real64, gjentakelsesintervall xml_buffer
    -> ListExploder
Trafikkreguleringer (reader GML_1)
    attributes: identifikasjon.Identifikasjon.lokalId xml_buffer, identifikasjon.Identifikasjon.navnerom xml_buffer, identifikasjon.Identifikasjon.versjonId xml_buffer, endringsflagg.Endringsflagg.typeEndring xml_buffer, trafikkreguleringer xml_buffer, senterlinje xml_geometry, lineærPosisjon{}.LineærPosisjonStrekning.lenkesekvens.Identifikasjon.lokalId xml_buffer, lineærPosisjon{}.LineærPosisjonStrekning.lenkesekvens.Identifikasjon.navnerom xml_buffer, lineærPosisjon{}.LineærPosisjonStrekning.lenkesekvens.Identifikasjon.versjonId xml_buffer, lineærPosisjon{}.LineærPosisjonStrekning.lineærReferanseMetode xml_buffer, lineærPosisjon{}.LineærPosisjonStrekning.retning xml_buffer, lineærPosisjon{}.LineærPosisjonStrekning.fraPosisjon xml_real64, lineærPosisjon{}.LineærPosisjonStrekning.tilPosisjon xml_real64
    -> ListExploder
Svingerestriksjon (reader GML_1)
    attributes: identifikasjon.Identifikasjon.lokalId xml_buffer, identifikasjon.Identifikasjon.navnerom xml_buffer, identifikasjon.Identifikasjon.versjonId xml_buffer, endringsflagg.Endringsflagg.typeEndring xml_buffer, posisjon xml_geometry, svingeforbudFra.LineærPosisjonPunkt.lenkesekvens.Identifikasjon.lokalId xml_buffer, svingeforbudFra.LineærPosisjonPunkt.lenkesekvens.Identifikasjon.navnerom xml_buffer, svingeforbudFra.LineærPosisjonPunkt.lenkesekvens.Identifikasjon.versjonId xml_buffer, svingeforbudFra.LineærPosisjonPunkt.lineærReferanseMetode xml_buffer, svingeforbudFra.LineærPosisjonPunkt.posisjon xml_real64, svingeforbudTil.LineærPosisjonPunkt.lenkesekvens.Identifikasjon.lokalId xml_buffer, svingeforbudTil.LineærPosisjonPunkt.lenkesekvens.Identifikasjon.navnerom xml_buffer, svingeforbudTil.LineærPosisjonPunkt.lenkesekvens.Identifikasjon.versjonId xml_buffer, svingeforbudTil.LineærPosisjonPunkt.lineærReferanseMetode xml_buffer, svingeforbudTil.LineærPosisjonPunkt.posisjon xml_real64
    -> ListExploder
Landbruksvegklasse (reader GML_1)
    attributes: identifikasjon.Identifikasjon.lokalId xml_buffer, identifikasjon.Identifikasjon.navnerom xml_buffer, identifikasjon.Identifikasjon.versjonId xml_buffer, endringsflagg.Endringsflagg.typeEndring xml_buffer, klasseLandbruksveg xml_buffer, senterlinje xml_geometry, lineærPosisjon{}.LineærPosisjonStrekning.lenkesekvens.Identifikasjon.lokalId xml_buffer, lineærPosisjon{}.LineærPosisjonStrekning.lenkesekvens.Identifikasjon.navnerom xml_buffer, lineærPosisjon{}.LineærPosisjonStrekning.lenkesekvens.Identifikasjon.versjonId xml_buffer, lineærPosisjon{}.LineærPosisjonStrekning.lineærReferanseMetode xml_buffer, lineærPosisjon{}.LineærPosisjonStrekning.retning xml_buffer, lineærPosisjon{}.LineærPosisjonStrekning.fraPosisjon xml_real64, lineærPosisjon{}.LineærPosisjonStrekning.tilPosisjon xml_real64
    -> ListExploder
Jernbanekryssing (reader GML_1)
    attributes: identifikasjon.Identifikasjon.lokalId xml_buffer, identifikasjon.Identifikasjon.navnerom xml_buffer, identifikasjon.Identifikasjon.versjonId xml_buffer, endringsflagg.Endringsflagg.typeEndring xml_buffer, typeJernbanekryssing xml_buffer, posisjon xml_geometry, lineærPosisjon.LineærPosisjonPunkt.lineærReferanseMetode xml_buffer, lineærPosisjon.LineærPosisjonPunkt.lenkesekvens.Identifikasjon.lokalId xml_buffer, lineærPosisjon.LineærPosisjonPunkt.lenkesekvens.Identifikasjon.navnerom xml_buffer, lineærPosisjon.LineærPosisjonPunkt.lenkesekvens.Identifikasjon.versjonId xml_buffer, lineærPosisjon.LineærPosisjonPunkt.posisjon xml_real64
    -> ListExploder
InnkjøringForbudt (reader GML_1)
    attributes: identifikasjon.Identifikasjon.lokalId xml_buffer, identifikasjon.Identifikasjon.navnerom xml_buffer, identifikasjon.Identifikasjon.versjonId xml_buffer, endringsflagg.Endringsflagg.typeEndring xml_buffer, senterlinje xml_geometry, lineærPosisjon{}.LineærPosisjonStrekning.lenkesekvens.Identifikasjon.lokalId xml_buffer, lineærPosisjon{}.LineærPosisjonStrekning.lenkesekvens.Identifikasjon.navnerom xml_buffer, lineærPosisjon{}.LineærPosisjonStrekning.lenkesekvens.Identifikasjon.versjonId xml_buffer, lineærPosisjon{}.LineærPosisjonStrekning.lineærReferanseMetode xml_buffer, lineærPosisjon{}.LineærPosisjonStrekning.retning xml_buffer, lineærPosisjon{}.LineærPosisjonStrekning.fraPosisjon xml_real64, lineærPosisjon{}.LineærPosisjonStrekning.tilPosisjon xml_real64
    -> ListExploder
Høydebegrensning (reader GML_1)
    attributes: identifikasjon.Identifikasjon.lokalId xml_buffer, identifikasjon.Identifikasjon.navnerom xml_buffer, identifikasjon.Identifikasjon.versjonId xml_buffer, endringsflagg.Endringsflagg.typeEndring xml_buffer, skiltaHøyde xml_real64, typeHinderHøydebegrensning xml_buffer, senterlinje xml_geometry, lineærPosisjon{}.LineærPosisjonStrekning.lenkesekvens.Identifikasjon.lokalId xml_buffer, lineærPosisjon{}.LineærPosisjonStrekning.lenkesekvens.Identifikasjon.navnerom xml_buffer, lineærPosisjon{}.LineærPosisjonStrekning.lenkesekvens.Identifikasjon.versjonId xml_buffer, lineærPosisjon{}.LineærPosisjonStrekning.lineærReferanseMetode xml_buffer, lineærPosisjon{}.LineærPosisjonStrekning.retning xml_buffer, lineærPosisjon{}.LineærPosisjonStrekning.fraPosisjon xml_real64, lineærPosisjon{}.LineærPosisjonStrekning.tilPosisjon xml_real64
    -> ListExploder
Gågatereguleringer (reader GML_1)
    attributes: identifikasjon.Identifikasjon.lokalId xml_buffer, identifikasjon.Identifikasjon.navnerom xml_buffer, identifikasjon.Identifikasjon.versjonId xml_buffer, endringsflagg.Endringsflagg.typeEndring xml_buffer, varetransportHverdagULørdagPeriode1FraKl xml_buffer, varetransportHverdagULørdagPeriode1TilKl xml_buffer, varetransportHverdagULørdagPeriode2FraKl xml_buffer, varetransportHverdagULørdagPeriode2TilKl xml_buffer, varetransportLørdagFra xml_buffer, varetransportLørdagTil xml_buffer, kjøringTilEiendommeneTillatt xml_buffer, senterlinje xml_geometry, lineærPosisjon{}.LineærPosisjonStrekning.lenkesekvens.Identifikasjon.lokalId xml_buffer, lineærPosisjon{}.LineærPosisjonStrekning.lenkesekvens.Identifikasjon.navnerom xml_buffer, lineærPosisjon{}.LineærPosisjonStrekning.lenkesekvens.Identifikasjon.versjonId xml_buffer, lineærPosisjon{}.LineærPosisjonStrekning.lineærReferanseMetode xml_buffer, lineærPosisjon{}.LineærPosisjonStrekning.retning xml_buffer, lineærPosisjon{}.LineærPosisjonStrekning.fraPosisjon xml_real64, lineærPosisjon{}.LineærPosisjonStrekning.tilPosisjon xml_real64
    -> ListExploder
FunksjonellVegklasse (reader GML_1)
    attributes: identifikasjon.Identifikasjon.lokalId xml_buffer, identifikasjon.Identifikasjon.navnerom xml_buffer, identifikasjon.Identifikasjon.versjonId xml_buffer, endringsflagg.Endringsflagg.typeEndring xml_buffer, vegklasse xml_buffer, senterlinje xml_geometry, lineærPosisjon{}.LineærPosisjonStrekning.lenkesekvens.Identifikasjon.lokalId xml_buffer, lineærPosisjon{}.LineærPosisjonStrekning.lenkesekvens.Identifikasjon.navnerom xml_buffer, lineærPosisjon{}.LineærPosisjonStrekning.lenkesekvens.Identifikasjon.versjonId xml_buffer, lineærPosisjon{}.LineærPosisjonStrekning.lineærReferanseMetode xml_buffer, lineærPosisjon{}.LineærPosisjonStrekning.retning xml_buffer, lineærPosisjon{}.LineærPosisjonStrekning.fraPosisjon xml_real64, lineærPosisjon{}.LineærPosisjonStrekning.tilPosisjon xml_real64
    -> ListExploder
Fartsgrense (reader GML_1)
    attributes: identifikasjon.Identifikasjon.lokalId xml_buffer, identifikasjon.Identifikasjon.navnerom xml_buffer, identifikasjon.Identifikasjon.versjonId xml_buffer, endringsflagg.Endringsflagg.typeEndring xml_buffer, fartsgrenseVerdi xml_buffer, senterlinje xml_geometry, lineærPosisjon{}.LineærPosisjonStrekning.lenkesekvens.Identifikasjon.lokalId xml_buffer, lineærPosisjon{}.LineærPosisjonStrekning.lenkesekvens.Identifikasjon.navnerom xml_buffer, lineærPosisjon{}.LineærPosisjonStrekning.lenkesekvens.Identifikasjon.versjonId xml_buffer, lineærPosisjon{}.LineærPosisjonStrekning.lineærReferanseMetode xml_buffer, lineærPosisjon{}.LineærPosisjonStrekning.retning xml_buffer, lineærPosisjon{}.LineærPosisjonStrekning.fraPosisjon xml_real64, lineærPosisjon{}.LineærPosisjonStrekning.tilPosisjon xml_real64
    -> ListExploder
Note: Pakker ut liste for lineærPosisjon
ListExploder
    ATTR_ACCUM_MODE = Merge Incoming List
    ATTR_CONFLICT_RES = Use Incoming List
    INDEX_ATTR = _element_index
    LIST_ATTR = lineærPosisjon{}
    ELEMENTS -> BulkAttributeRenamer_2
    <REJECTED> -> BulkAttributeRenamer_2
Note: Fjerner eventuelt gjenværende lineærPosisjon-prefikser
BulkAttributeRenamer_2
    ATTRCHOICE = All Attributes
    CASE_DISP = YES
    MODE_CHOICE = RENAME
    PATTERN_ACTION_DISP = REMOVEPREFIX
    REPLACE_STR = lineærPosisjon.
    -> AttributeExposer
AttributeExposer
    ATTR_LIST = fme_feature_type
    -> SchemaMapper_2
Note: Mapper attributtnavn til SOSI-navn
SchemaMapper_2
    CSV2_CASE_SENSITIVE_FIELD_NAMES = Yes
    CSV2_DATA_START_LINE = 2
    CSV2_DELIMITER = ;
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_SKIPPED_LINES = No
    CSV2_SCAN_ADDITIONAL_FIELDS = No
    CSV2_SCAN_MAX_ROWS = 1000
    CSV2_SCAN_TYPES = No
    CSV2_SKIP_DUPLICATE_DELIMITERS = No
    CSV2_TRIM_FIELD_NAME_QUALIFIERS = Yes
    CSV2_TRIM_FIELD_VALUE_QUALIFIERS = Yes
    CSV2_USE_CUSTOM_SCHEMA = NO
    DATASET = C:\DATA\GitHub\NVDBGML\XSD\NVDB\fkbvn\fkbvn_ptSOSIMapping.csv
    FORMAT = CSV2
    IDXDESTATTR = fme_feature_type
    IDXDESTCOL = ""
    IDXSOURCEATTR = fme_feature_type
    IDXSOURCECOL = ""
    MAP_ATTRS = name ptid $(FME_ASC_16)
    MATCH_ATTRS = ft_attr ftid
    ROW_ID_ATTR = _schemamapper_row_ids
    TABLE = CSV
    MAPPED -> BulkAttributeRenamer
Veglenke (reader GML_1)
    attributes: identifikasjon.Identifikasjon.lokalId xml_buffer, identifikasjon.Identifikasjon.navnerom xml_buffer, identifikasjon.Identifikasjon.versjonId xml_buffer, datafangstdato xml_date, endringsflagg.Endringsflagg.typeEndring xml_buffer, kvalitet.Posisjonskvalitet.målemetode xml_buffer, kvalitet.Posisjonskvalitet.nøyaktighet xml_int64, kvalitet.Posisjonskvalitet.synbarhet xml_buffer, kvalitet.Posisjonskvalitet.målemetodeHøyde xml_buffer, kvalitet.Posisjonskvalitet.nøyaktighetHøyde xml_int64, kvalitet.Posisjonskvalitet.maksimaltAvvik xml_int64, medium xml_buffer, standardLRM xml_buffer, detaljnivå xml_buffer, feltoversikt xml_buffer, konnekteringslenke xml_boolean, senterlinje xml_geometry, typeVeg xml_buffer, veglenkeadresse.Veglenkeadresse.adressekode xml_int64, veglenkeadresse.Veglenkeadresse.adressenavn xml_buffer, veglenkeadresse.Veglenkeadresse.sideveg xml_buffer, vegreferanse.Vegreferanse.vegkategori xml_buffer, vegreferanse.Vegreferanse.vegnummer xml_int64, vegreferanse.Vegreferanse.vegstatus xml_buffer, vegreferanse.Vegreferanse.hovedparsell xml_int64, vegreferanse.Vegreferanse.veglenkeMeterFra xml_int64, vegreferanse.Vegreferanse.veglenkeMeterTil xml_int64, vegreferanse.Vegreferanse.referanseretning xml_buffer, vegreferanse.Vegreferanse.vegreferanseFraDato xml_date, kommunenummer xml_buffer,
      lenkesekvens.Lenkesekvensreferanse.identifikasjon.Identifikasjon.lokalId xml_buffer, lenkesekvens.Lenkesekvensreferanse.identifikasjon.Identifikasjon.navnerom xml_buffer, lenkesekvens.Lenkesekvensreferanse.identifikasjon.Identifikasjon.versjonId xml_buffer, lenkesekvens.Lenkesekvensreferanse.startposisjon xml_real64, lenkesekvens.Lenkesekvensreferanse.sluttposisjon xml_real64
    -> Veglenke
    -> BulkAttributeRenamer
Veglenke: Inspector
Note: Setter alle attributtnavn til store bokstaver
BulkAttributeRenamer
    ATTRCHOICE = All Attributes
    CASE_CHANGE_TYPE = upper
    MODE_CHOICE = RENAME
    PATTERN_ACTION_DISP = CASECHANGE
    -> AttributeManager
Note: Individuelle endringer for en del attributter
AttributeManager
    ATTR_TABLE:
      REMOVE GML_PARENT_ID
      REMOVE GML_PARENT_PROPERTY
      REMOVE GML_ID
      RENAME_SET_VALUE IDENTIFIKASJON.IDENTIFIKASJON.LOKALID > IDENT.LOKALID
      RENAME_SET_VALUE IDENTIFIKASJON.IDENTIFIKASJON.NAVNEROM > IDENT.NAVNEROM
      RENAME_SET_VALUE IDENTIFIKASJON.IDENTIFIKASJON.VERSJONID > IDENT.VERSJONID
      REMOVE ENDRINGSFLAGG.ENDRINGSFLAGG.TYPEENDRING
      RENAME_SET_VALUE KVALITET.POSISJONSKVALITET.MÅLEMETODE > KVALITET.MÅLEMETODE
      RENAME_SET_VALUE KVALITET.POSISJONSKVALITET.NØYAKTIGHET > KVALITET.NØYAKTIGHET
      RENAME_SET_VALUE KVALITET.POSISJONSKVALITET.SYNBARHET > KVALITET.SYNBARHET
      RENAME_SET_VALUE KVALITET.POSISJONSKVALITET.MÅLEMETODEHØYDE > KVALITET.MÅLEMETODEHØYDE
      RENAME_SET_VALUE KVALITET.POSISJONSKVALITET.NØYAKTIGHETHØYDE > KVALITET.NØYAKTIGHETHØYDE
      RENAME_SET_VALUE KVALITET.POSISJONSKVALITET.MAKSIMALTAVVIK > KVALITET.MAKSIMALTAVVIK
      RENAME_SET_VALUE STANDARDLRM > LRLRM = FME_CONDITIONAL:DEFAULT_VALUE'_FME_NO_OP_'BOOL_OP;OR;COMPOSITE_TEST;<Unused>;TEST @Value(LRLRM) = metrering'1'BOOL_OP;OR;COMPOSITE_TEST;<Unused>;TEST @Value(LRLRM) = kilometrering'2'BOOL_OP;OR;COMPOSITE_TEST;<Unused>;TEST @Value(LRLRM) = normalisert'3'BOOL_OP;OR;COMPOSITE_TEST;<Unused>;TEST @Value(LRLRM) = prosent'5'FME_NUM_CONDITIONS5___
      RENAME_SET_VALUE DETALJNIVÅ > VEGDETALJNIVÅ
      SET_TO KONNEKTERINGSLENKE = FME_CONDITIONAL:DEFAULT_VALUE'_FME_NO_OP_'BOOL_OP;OR;COMPOSITE_TEST;<Unused>;TEST @Value(KONNEKTERINGSLENKE) = true'JA'BOOL_OP;OR;COMPOSITE_TEST;<Unused>;TEST @Value(KONNEKTERINGSLENKE) = false'NEI'FME_NUM_CONDITIONS3___
      RENAME_SET_VALUE VEGLENKEADRESSE.VEGLENKEADRESSE.ADRESSEKODE > VEGLENKEADRESSE.ADRESSEKODE
      RENAME_SET_VALUE VEGLENKEADRESSE.VEGLENKEADRESSE.ADRESSENAVN > VEGLENKEADRESSE.ADRESSENAVN
      RENAME_SET_VALUE VEGLENKEADRESSE.VEGLENKEADRESSE.SIDEVEG > VEGLENKEADRESSE.SIDEVEG = FME_CONDITIONAL:DEFAULT_VALUE'_FME_NO_OP_'BOOL_OP;OR;COMPOSITE_TEST;<Unused>;TEST @Value(VEGLENKEADRESSE.SIDEVEG) = true'JA'BOOL_OP;OR;COMPOSITE_TEST;<Unused>;TEST @Value(VEGLENKEADRESSE.SIDEVEG) = false'NEI'FME_NUM_CONDITIONS3___
      RENAME_SET_VALUE VEGREFERANSE.VEGREFERANSE.VEGKATEGORI > VREF.NVDB_VEGKATEGORI
      RENAME_SET_VALUE VEGREFERANSE.VEGREFERANSE.VEGSTATUS > VREF.NVDB_VEGSTATUS
      RENAME_SET_VALUE VEGREFERANSE.VEGREFERANSE.VEGNUMMER > VREF.VEGNUMMER
      RENAME_SET_VALUE VEGREFERANSE.VEGREFERANSE.HOVEDPARSELL > VREF.HOVEDPARSELL
      RENAME_SET_VALUE VEGREFERANSE.VEGREFERANSE.VEGLENKEMETERFRA > VREF.METERFRA
      RENAME_SET_VALUE VEGREFERANSE.VEGREFERANSE.VEGLENKEMETERTIL > VREF.METERTIL
      RENAME_SET_VALUE VEGREFERANSE.VEGREFERANSE.REFERANSERETNING > VREF.REFERANSERETNING
      RENAME_SET_VALUE VEGREFERANSE.VEGREFERANSE.VEGREFERANSEFRADATO > VREF.VFRADATO
      REMOVE SENTERLINJE
      REMOVE _SCHEMAMAPPER_ROW_IDS
      RENAME_SET_VALUE LINEÆRPOSISJONSTREKNING.LENKESEKVENS.IDENTIFIKASJON.LOKALID > LRPOSISJON.LENKESEKVENS.IDENT.LOKALID
      RENAME_SET_VALUE LINEÆRPOSISJONSTREKNING.LENKESEKVENS.IDENTIFIKASJON.NAVNEROM > LRPOSISJON.LENKESEKVENS.IDENT.NAVNEROM
      RENAME_SET_VALUE LINEÆRPOSISJONSTREKNING.LENKESEKVENS.IDENTIFIKASJON.VERSJONID > LRPOSISJON.LENKESEKVENS.IDENT.VERSJONID
      RENAME_SET_VALUE LINEÆRPOSISJONSTREKNING.LINEÆRREFERANSEMETODE > LRPOSISJON.LRLRM
      RENAME_SET_VALUE LINEÆRPOSISJONSTREKNING.RETNING > LRPOSISJON.RETNING
      RENAME_SET_VALUE LINEÆRPOSISJONSTREKNING.FRAPOSISJON > LRPOSISJON.LRFRAPOSISJON
      RENAME_SET_VALUE LINEÆRPOSISJONSTREKNING.TILPOSISJON > LRPOSISJON.LRTILPOSISJON
      REMOVE _ELEMENT_INDEX
      RENAME_SET_VALUE VARETRANSPORTHVERDAGULØRDAGPERIODE1FRAKL > VARETRANSPORT_HVERDAG_1_FRA
      RENAME_SET_VALUE VARETRANSPORTHVERDAGULØRDAGPERIODE1TILKL > VARETRANSPORT_HVERDAG_1_TIL
      RENAME_SET_VALUE VARETRANSPORTHVERDAGULØRDAGPERIODE2FRAKL > VARETRANSPORT_HVERDAG_2_FRA
      RENAME_SET_VALUE VARETRANSPORTHVERDAGULØRDAGPERIODE2TILKL > VARETRANSPORT_HVERDAG_2_TIL
      RENAME_SET_VALUE VARETRANSPORTLØRDAGFRA > VARETRANSPORT_LØRDAG_FRA
      RENAME_SET_VALUE VARETRANSPORTLØRDAGTIL > VARETRANSPORT_LØRDAG_TIL
      RENAME_SET_VALUE KJØRINGTILEIENDOMMENETILLATT > KJØRING_TIL_EIENDOM_TILLAT
      RENAME_SET_VALUE LINEÆRPOSISJONPUNKT.LENKESEKVENS.IDENTIFIKASJON.LOKALID > LRPOSISJON.LENKESEKVENS.IDENT.LOKALID
      RENAME_SET_VALUE LINEÆRPOSISJONPUNKT.LENKESEKVENS.IDENTIFIKASJON.NAVNEROM > LRPOSISJON.LENKESEKVENS.IDENT.NAVNEROM
      RENAME_SET_VALUE LINEÆRPOSISJONPUNKT.LENKESEKVENS.IDENTIFIKASJON.VERSJONID > LRPOSISJON.LENKESEKVENS.IDENT.VERSJONID
      RENAME_SET_VALUE LINEÆRPOSISJONPUNKT.LINEÆRREFERANSEMETODE > LRPOSISJON.LRLRM
      RENAME_SET_VALUE LINEÆRPOSISJONPUNKT.POSISJON > LRPOSISJON.LRPUNKTPOSISJON
      RENAME_SET_VALUE SVINGEFORBUDFRA.LINEÆRPOSISJONPUNKT.LENKESEKVENS.IDENTIFIKASJON.LOKALID > SVINGEFORBUDFRA.LRPOSISJON.LENKESEKVENS.IDENT.LOKALID
      RENAME_SET_VALUE SVINGEFORBUDFRA.LINEÆRPOSISJONPUNKT.LENKESEKVENS.IDENTIFIKASJON.NAVNEROM > SVINGEFORBUDFRA.LRPOSISJON.LENKESEKVENS.IDENT.NAVNEROM
      RENAME_SET_VALUE SVINGEFORBUDFRA.LINEÆRPOSISJONPUNKT.LENKESEKVENS.IDENTIFIKASJON.VERSJONID > SVINGEFORBUDFRA.LRPOSISJON.LENKESEKVENS.IDENT.VERSJONID
      RENAME_SET_VALUE SVINGEFORBUDFRA.LINEÆRPOSISJONPUNKT.LINEÆRREFERANSEMETODE > SVINGEFORBUDFRA.LRPOSISJON.LRLRM
      RENAME_SET_VALUE SVINGEFORBUDFRA.LINEÆRPOSISJONPUNKT.POSISJON > SVINGEFORBUDFRA.LRPOSISJON.LRPUNKTPOSISJON
      RENAME_SET_VALUE SVINGEFORBUDTIL.LINEÆRPOSISJONPUNKT.LENKESEKVENS.IDENTIFIKASJON.LOKALID > SVINGEFORBUDTIL.LRPOSISJON.LENKESEKVENS.IDENT.LOKALID
      RENAME_SET_VALUE SVINGEFORBUDTIL.LINEÆRPOSISJONPUNKT.LENKESEKVENS.IDENTIFIKASJON.NAVNEROM > SVINGEFORBUDTIL.LRPOSISJON.LENKESEKVENS.IDENT.NAVNEROM
      RENAME_SET_VALUE SVINGEFORBUDTIL.LINEÆRPOSISJONPUNKT.LENKESEKVENS.IDENTIFIKASJON.VERSJONID > SVINGEFORBUDTIL.LRPOSISJON.LENKESEKVENS.IDENT.VERSJONID
      RENAME_SET_VALUE SVINGEFORBUDTIL.LINEÆRPOSISJONPUNKT.LINEÆRREFERANSEMETODE > SVINGEFORBUDTIL.LRPOSISJON.LRLRM
      RENAME_SET_VALUE SVINGEFORBUDTIL.LINEÆRPOSISJONPUNKT.POSISJON > SVINGEFORBUDTIL.LRPOSISJON.LRPUNKTPOSISJON
      SET_TO LRPOSISJON.LRLRM = FME_CONDITIONAL:DEFAULT_VALUE'_FME_NO_OP_'BOOL_OP;OR;COMPOSITE_TEST;<Unused>;TEST @Value(LRPOSISJON.LRLRM) = metrering'1'BOOL_OP;OR;COMPOSITE_TEST;<Unused>;TEST @Value(LRPOSISJON.LRLRM) = kilometrering'2'BOOL_OP;OR;COMPOSITE_TEST;<Unused>;TEST @Value(LRPOSISJON.LRLRM) = normalisert'3'BOOL_OP;OR;COMPOSITE_TEST;<Unused>;TEST @Value(LRPOSISJON.LRLRM) = prosent'5'FME_NUM_CONDITIONS5___
      RENAME_SET_VALUE LENKESEKVENS.LENKESEKVENSREFERANSE.IDENTIFIKASJON.IDENTIFIKASJON.LOKALID > LENKESEKVENS.IDENT.LOKALID
      RENAME_SET_VALUE LENKESEKVENS.LENKESEKVENSREFERANSE.IDENTIFIKASJON.IDENTIFIKASJON.NAVNEROM > LENKESEKVENS.IDENT.NAVNEROM
      RENAME_SET_VALUE LENKESEKVENS.LENKESEKVENSREFERANSE.IDENTIFIKASJON.IDENTIFIKASJON.VERSJONID > LENKESEKVENS.IDENT.VERSJONID
      RENAME_SET_VALUE LENKESEKVENS.LENKESEKVENSREFERANSE.STARTPOSISJON > LRSTARTVERDI
      RENAME_SET_VALUE LENKESEKVENS.LENKESEKVENSREFERANSE.SLUTTPOSISJON > LRSLUTTVERDI
      SET_TO VEGLENKEADRESSE.KOMMUNENUMMER = @Value(KOMMUNENUMMER)
    -> DateFormatter
Note: Formaterer datoer
DateFormatter
    DATE_ATTR = VREF.VFRADATO,DATAFANGSTDATO
    FMT = %Y%m%d
    INVALID_DATE_VALUE = _FME_NO_OP_
    SRCFMT = Unknown - Automatic Detection
    -> Sampler_2
    -> Veglenke (writer GDMMAPPERSOSI_1)
    -> Sc
Sampler_2 [off]
    GROUP_BY = fme_feature_type
    RATE = 250
    SAMPLE_MODE = Yes
    SAMPLE_TYPE_LONG = Every Nth Feature
    SAMPLED -> Veglenke (writer GDMMAPPERSOSI_1)
Veglenke (writer GDMMAPPERSOSI_1)
    attributes: IDENT.LOKALID varchar(200), IDENT.NAVNEROM varchar(200), IDENT.VERSJONID varchar(200), DATAFANGSTDATO varchar(200), KVALITET.MÅLEMETODE varchar(200), KVALITET.NØYAKTIGHET varchar(200), KVALITET.SYNBARHET varchar(200), KVALITET.MÅLEMETODEHØYDE varchar(200), KVALITET.NØYAKTIGHETHØYDE varchar(200), KVALITET.MAKSIMALTAVVIK varchar(200), MEDIUM varchar(200), LRLRM varchar(200), VEGDETALJNIVÅ varchar(200), FELTOVERSIKT varchar(200), KONNEKTERINGSLENKE varchar(200), TYPEVEG varchar(200), VEGLENKEADRESSE.ADRESSEKODE varchar(200), VEGLENKEADRESSE.ADRESSENAVN varchar(200), VEGLENKEADRESSE.SIDEVEG varchar(200), VREF.NVDB_VEGKATEGORI varchar(200), VREF.NVDB_VEGSTATUS varchar(200), VREF.VEGNUMMER varchar(200), VREF.HOVEDPARSELL varchar(200), VREF.METERFRA varchar(200), VREF.METERTIL varchar(200), VREF.REFERANSERETNING varchar(200), VREF.VFRADATO varchar(200), FARTSGRENSEVERDI varchar(200), LRPOSISJON.RETNING varchar(200), LRPOSISJON.LRFRAPOSISJON varchar(200),
      LRPOSISJON.LRTILPOSISJON varchar(200), VEGKLASSE varchar(200), VARETRANSPORT_HVERDAG_1_FRA varchar(200), VARETRANSPORT_HVERDAG_1_TIL varchar(200), VARETRANSPORT_HVERDAG_2_FRA varchar(200), VARETRANSPORT_HVERDAG_2_TIL varchar(200), VARETRANSPORT_LØRDAG_FRA varchar(200), VARETRANSPORT_LØRDAG_TIL varchar(200), KJØRING_TIL_EIENDOM_TILLAT varchar(200), KLASSELANDBRUKSVEG varchar(200), TYPEJERNBANEKRYSSING varchar(200), POSISJON varchar(200), LRPOSISJON.LENKESEKVENS.IDENT.LOKALID varchar(200), LRPOSISJON.LENKESEKVENS.IDENT.NAVNEROM varchar(200), LRPOSISJON.LENKESEKVENS.IDENT.VERSJONID varchar(200), LRPOSISJON.LRPUNKTPOSISJON varchar(200), HØYFJELLSSTREKNING varchar(200), VINTERSTENGT_FRADATO varchar(200), VINTERSTENGT_TILDATO varchar(200), HOVEDPROBLEM varchar(200), SKILTAHØYDE varchar(200), TYPEHINDERHØYDEBEGRENSNING varchar(200), TRAFIKKREGULERINGER varchar(200), TYPE varchar(200), SVINGEFORBUDFRA.LRPOSISJON.LENKESEKVENS.IDENT.LOKALID varchar(200), SVINGEFORBUDFRA.LRPOSISJON.LENKESEKVENS.IDENT.NAVNEROM varchar(200), SVINGEFORBUDFRA.LRPOSISJON.LENKESEKVENS.IDENT.VERSJONID varchar(200), SVINGEFORBUDFRA.LRPOSISJON.LRLRM varchar(200), SVINGEFORBUDFRA.LRPOSISJON.LRPUNKTPOSISJON varchar(200), SVINGEFORBUDTIL.LRPOSISJON.LENKESEKVENS.IDENT.LOKALID varchar(200),
      SVINGEFORBUDTIL.LRPOSISJON.LENKESEKVENS.IDENT.NAVNEROM varchar(200), SVINGEFORBUDTIL.LRPOSISJON.LENKESEKVENS.IDENT.VERSJONID varchar(200), SVINGEFORBUDTIL.LRPOSISJON.LRLRM varchar(200), SVINGEFORBUDTIL.LRPOSISJON.LRPUNKTPOSISJON varchar(200), fme_rejection_code varchar(200), LRPOSISJON.LRLRM varchar(200), KOMMUNENUMMER varchar(200), LENKESEKVENS.IDENT.LOKALID varchar(200), LENKESEKVENS.IDENT.NAVNEROM varchar(200), LENKESEKVENS.IDENT.VERSJONID varchar(200), LRSTARTVERDI varchar(200), LRSLUTTVERDI varchar(200), GJENTAKELSESINTERVALL varchar(200), VEGLENKEADRESSE.KOMMUNENUMMER varchar(200)
Sc: Inspector [off]
    TACKATTRS = fme_feature_type
