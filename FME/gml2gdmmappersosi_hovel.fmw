FME workspace gml2gdmmappersosi_hovel.fmw

Parameters:
- kommune = 0417   # Kommune
- mainFolder = C:\DATA\Standardisering\fme   # Hovedmappe
- SourceDataset_GML_8 = $(fullFolder)\*.gml   # Source Geography Markup Language (GML) File(s)
- SourceDataset_GML_9 = $(fullFolder)\*.gml   # Source Geography Markup Language (GML) File(s)
- fullFolder:   # Python Script
      fldr = FME_MacroValues['mainFolder'] + '\\kommune\\' + FME_MacroValues['kommune']
      return fldr

Readers:
- GML_4: GML from $(SourceDataset_GML_8)
- GML_6: GML from $(SourceDataset_GML_9)

Writers:
- GDMMAPPERSOSI_1: GDMMAPPERSOSI to $(kommune) in ETRS89.UTM-33N

Beredskapsveg (reader GML_4)
    attributes: identifikasjon.Identifikasjon.lokalId xml_buffer, identifikasjon.Identifikasjon.navnerom xml_buffer, identifikasjon.Identifikasjon.versjonId xml_buffer, oppdateringsdato xml_datetime, senterlinje xml_geometry, lineærPosisjon{}.LineærPosisjonStrekning.felt xml_buffer, lineærPosisjon{}.LineærPosisjonStrekning.sideposisjon xml_buffer, lineærPosisjon{}.LineærPosisjonStrekning.høydeposisjon xml_buffer, lineærPosisjon{}.LineærPosisjonStrekning.fraPosisjon xml_real64, lineærPosisjon{}.LineærPosisjonStrekning.tilPosisjon xml_real64
    -> ListExploder
Fartsgrense (reader GML_4)
    attributes: identifikasjon.Identifikasjon.lokalId xml_buffer, identifikasjon.Identifikasjon.navnerom xml_buffer, identifikasjon.Identifikasjon.versjonId xml_buffer, oppdateringsdato xml_datetime, fartsgrenseVerdi xml_buffer, vedtaksnummer xml_buffer, gyldigFraDato xml_date, arkivnummer xml_buffer, senterlinje xml_geometry, lineærPosisjon{}.LineærPosisjonStrekning.felt xml_buffer, lineærPosisjon{}.LineærPosisjonStrekning.sideposisjon xml_buffer, lineærPosisjon{}.LineærPosisjonStrekning.høydeposisjon xml_buffer, lineærPosisjon{}.LineærPosisjonStrekning.fraPosisjon xml_real64, lineærPosisjon{}.LineærPosisjonStrekning.tilPosisjon xml_real64
    -> ListExploder
FartsgrenseVariabel (reader GML_4)
    attributes: identifikasjon.Identifikasjon.lokalId xml_buffer, identifikasjon.Identifikasjon.navnerom xml_buffer, identifikasjon.Identifikasjon.versjonId xml_buffer, oppdateringsdato xml_datetime, fartsgrenseVerdi xml_buffer, type xml_buffer, ukedag xml_buffer, datoFra xml_buffer, datoTil xml_buffer, klokkeslettFra xml_buffer, klokkeslettTil xml_buffer, vedtaksnummer xml_buffer, gyldigFraDato xml_date, merknad xml_buffer, arkivnummer xml_buffer, prosjektreferanse xml_buffer, senterlinje xml_geometry, lineærPosisjon{}.LineærPosisjonStrekning.felt xml_buffer, lineærPosisjon{}.LineærPosisjonStrekning.sideposisjon xml_buffer, lineærPosisjon{}.LineærPosisjonStrekning.høydeposisjon xml_buffer, lineærPosisjon{}.LineærPosisjonStrekning.fraPosisjon xml_real64, lineærPosisjon{}.LineærPosisjonStrekning.tilPosisjon xml_real64
    -> ListExploder
FunksjonellVegklasse (reader GML_4)
    attributes: identifikasjon.Identifikasjon.lokalId xml_buffer, identifikasjon.Identifikasjon.navnerom xml_buffer, identifikasjon.Identifikasjon.versjonId xml_buffer, oppdateringsdato xml_datetime, vegklasse xml_buffer, merknad xml_buffer, senterlinje xml_geometry, lineærPosisjon{}.LineærPosisjonStrekning.felt xml_buffer, lineærPosisjon{}.LineærPosisjonStrekning.sideposisjon xml_buffer, lineærPosisjon{}.LineærPosisjonStrekning.høydeposisjon xml_buffer, lineærPosisjon{}.LineærPosisjonStrekning.fraPosisjon xml_real64, lineærPosisjon{}.LineærPosisjonStrekning.tilPosisjon xml_real64
    -> ListExploder
Gågatereguleringer (reader GML_4)
    attributes: identifikasjon.Identifikasjon.lokalId xml_buffer, identifikasjon.Identifikasjon.navnerom xml_buffer, identifikasjon.Identifikasjon.versjonId xml_buffer, oppdateringsdato xml_datetime, varetransportHverdagULørdagPeriode1FraKl xml_buffer, varetransportHverdagULørdagPeriode1TilKl xml_buffer, varetransportHverdagULørdagPeriode2FraKl xml_buffer, varetransportHverdagULørdagPeriode2TilKl xml_buffer, varetransportLørdagPeriode1FraKl xml_buffer, varetransportLørdagPeriode1TilKl xml_buffer, varetransportLørdagPeriode2FraKl xml_buffer, varetransportLørdagPeriode2TilKl xml_buffer, kjøringTilEiendommeneTillatt xml_buffer, senterlinje xml_geometry, lineærPosisjon{}.LineærPosisjonStrekning.felt xml_buffer, lineærPosisjon{}.LineærPosisjonStrekning.sideposisjon xml_buffer, lineærPosisjon{}.LineærPosisjonStrekning.høydeposisjon xml_buffer, lineærPosisjon{}.LineærPosisjonStrekning.fraPosisjon xml_real64, lineærPosisjon{}.LineærPosisjonStrekning.tilPosisjon xml_real64
    -> ListExploder
Høydebegrensning (reader GML_4)
    attributes: identifikasjon.Identifikasjon.lokalId xml_buffer, identifikasjon.Identifikasjon.navnerom xml_buffer, identifikasjon.Identifikasjon.versjonId xml_buffer, oppdateringsdato xml_datetime, skiltaHøyde xml_real64, typeHinder xml_buffer, beregnetHøyde xml_real64, navn xml_buffer, merknad xml_buffer, bredde xml_real64, hMinHøyreKant xml_real64, hMinMidt xml_real64, hMinVenstreKant xml_real64, målemetode xml_buffer, måledato xml_date, prosjektreferanse xml_buffer, senterlinje xml_geometry, lineærPosisjon{}.LineærPosisjonStrekning.felt xml_buffer, lineærPosisjon{}.LineærPosisjonStrekning.sideposisjon xml_buffer, lineærPosisjon{}.LineærPosisjonStrekning.høydeposisjon xml_buffer, lineærPosisjon{}.LineærPosisjonStrekning.fraPosisjon xml_real64, lineærPosisjon{}.LineærPosisjonStrekning.tilPosisjon xml_real64
    -> ListExploder
InnkjøringForbudt (reader GML_4)
    attributes: identifikasjon.Identifikasjon.lokalId xml_buffer, identifikasjon.Identifikasjon.navnerom xml_buffer, identifikasjon.Identifikasjon.versjonId xml_buffer, oppdateringsdato xml_datetime, merknad xml_buffer, skiltnummer xml_buffer, senterlinje xml_geometry, lineærPosisjon{}.LineærPosisjonStrekning.felt xml_buffer, lineærPosisjon{}.LineærPosisjonStrekning.sideposisjon xml_buffer, lineærPosisjon{}.LineærPosisjonStrekning.høydeposisjon xml_buffer, lineærPosisjon{}.LineærPosisjonStrekning.fraPosisjon xml_real64, lineærPosisjon{}.LineærPosisjonStrekning.tilPosisjon xml_real64
    -> ListExploder
Jernbanekryssing (reader GML_4)
    attributes: identifikasjon.Identifikasjon.lokalId xml_buffer, identifikasjon.Identifikasjon.navnerom xml_buffer, identifikasjon.Identifikasjon.versjonId xml_buffer, oppdateringsdato xml_datetime, typeJernbanekryssing xml_buffer, tilleggsinformasjon xml_buffer, posisjon xml_geometry, lineærPosisjon{}.LineærPosisjonPunkt.felt xml_buffer, lineærPosisjon{}.LineærPosisjonPunkt.sideposisjon xml_buffer, lineærPosisjon{}.LineærPosisjonPunkt.høydeposisjon xml_buffer, lineærPosisjon{}.LineærPosisjonPunkt.posisjon xml_real64
    -> ListExploder
Landbruksvegklasse (reader GML_4)
    attributes: identifikasjon.Identifikasjon.lokalId xml_buffer, identifikasjon.Identifikasjon.navnerom xml_buffer, identifikasjon.Identifikasjon.versjonId xml_buffer, oppdateringsdato xml_datetime, klasseLandbruksveg xml_buffer, senterlinje xml_geometry, lineærPosisjon{}.LineærPosisjonStrekning.felt xml_buffer, lineærPosisjon{}.LineærPosisjonStrekning.sideposisjon xml_buffer, lineærPosisjon{}.LineærPosisjonStrekning.høydeposisjon xml_buffer, lineærPosisjon{}.LineærPosisjonStrekning.fraPosisjon xml_real64, lineærPosisjon{}.LineærPosisjonStrekning.tilPosisjon xml_real64
    -> ListExploder
Motorveg (reader GML_4)
    attributes: identifikasjon.Identifikasjon.lokalId xml_buffer, identifikasjon.Identifikasjon.navnerom xml_buffer, identifikasjon.Identifikasjon.versjonId xml_buffer, oppdateringsdato xml_datetime, motorvegtype xml_buffer, vedtaksnummer xml_buffer, arkivnummer xml_buffer, senterlinje xml_geometry, lineærPosisjon{}.LineærPosisjonStrekning.felt xml_buffer, lineærPosisjon{}.LineærPosisjonStrekning.sideposisjon xml_buffer, lineærPosisjon{}.LineærPosisjonStrekning.høydeposisjon xml_buffer, lineærPosisjon{}.LineærPosisjonStrekning.fraPosisjon xml_real64, lineærPosisjon{}.LineærPosisjonStrekning.tilPosisjon xml_real64
    -> ListExploder
Serviceveg (reader GML_4)
    attributes: identifikasjon.Identifikasjon.lokalId xml_buffer, identifikasjon.Identifikasjon.navnerom xml_buffer, identifikasjon.Identifikasjon.versjonId xml_buffer, oppdateringsdato xml_datetime, senterlinje xml_geometry, lineærPosisjon{}.LineærPosisjonStrekning.felt xml_buffer, lineærPosisjon{}.LineærPosisjonStrekning.sideposisjon xml_buffer, lineærPosisjon{}.LineærPosisjonStrekning.høydeposisjon xml_buffer, lineærPosisjon{}.LineærPosisjonStrekning.fraPosisjon xml_real64, lineærPosisjon{}.LineærPosisjonStrekning.tilPosisjon xml_real64
    -> ListExploder
Svingerestriksjon (reader GML_4)
    attributes: identifikasjon.Identifikasjon.lokalId xml_buffer, identifikasjon.Identifikasjon.navnerom xml_buffer, identifikasjon.Identifikasjon.versjonId xml_buffer, oppdateringsdato xml_datetime, merknad xml_buffer, posisjon xml_geometry, svingeforbudFra.LineærPosisjonPunkt.felt xml_buffer, svingeforbudFra.LineærPosisjonPunkt.sideposisjon xml_buffer, svingeforbudFra.LineærPosisjonPunkt.høydeposisjon xml_buffer, svingeforbudFra.LineærPosisjonPunkt.posisjon xml_real64, svingeforbudTil.LineærPosisjonPunkt.felt xml_buffer, svingeforbudTil.LineærPosisjonPunkt.sideposisjon xml_buffer, svingeforbudTil.LineærPosisjonPunkt.høydeposisjon xml_buffer, svingeforbudTil.LineærPosisjonPunkt.posisjon xml_real64
    -> ListExploder
Trafikkreguleringer (reader GML_4)
    attributes: identifikasjon.Identifikasjon.lokalId xml_buffer, identifikasjon.Identifikasjon.navnerom xml_buffer, identifikasjon.Identifikasjon.versjonId xml_buffer, oppdateringsdato xml_datetime, trafikkreguleringer xml_buffer, gjeldertidsrom xml_buffer, merknad xml_buffer, senterlinje xml_geometry, lineærPosisjon{}.LineærPosisjonStrekning.felt xml_buffer, lineærPosisjon{}.LineærPosisjonStrekning.sideposisjon xml_buffer, lineærPosisjon{}.LineærPosisjonStrekning.høydeposisjon xml_buffer, lineærPosisjon{}.LineærPosisjonStrekning.fraPosisjon xml_real64, lineærPosisjon{}.LineærPosisjonStrekning.tilPosisjon xml_real64
    -> ListExploder
Veglenke (reader GML_4)
    attributes: identifikasjon.Identifikasjon.lokalId xml_buffer, identifikasjon.Identifikasjon.navnerom xml_buffer, identifikasjon.Identifikasjon.versjonId xml_buffer, oppdateringsdato xml_datetime, datafangstdato xml_date, verifiseringsdato xml_date, kommunenummer xml_buffer, kommunenummer.codeSpace xml_buffer, kvalitet.Posisjonskvalitet.målemetode xml_buffer, kvalitet.Posisjonskvalitet.målemetode.codeSpace xml_buffer, kvalitet.Posisjonskvalitet.nøyaktighet xml_int64, kvalitet.Posisjonskvalitet.synbarhet xml_buffer, kvalitet.Posisjonskvalitet.målemetodeHøyde xml_buffer, kvalitet.Posisjonskvalitet.målemetodeHøyde.codeSpace xml_buffer, kvalitet.Posisjonskvalitet.nøyaktighetHøyde xml_int64, kvalitet.Posisjonskvalitet.maksimaltAvvik xml_int64, medium xml_buffer, standardLRM xml_buffer, lenkesekvens.Lenkesekvensreferanse.identifikasjon.Identifikasjon.lokalId xml_buffer, lenkesekvens.Lenkesekvensreferanse.identifikasjon.Identifikasjon.navnerom xml_buffer, lenkesekvens.Lenkesekvensreferanse.identifikasjon.Identifikasjon.versjonId xml_buffer, lenkesekvens.Lenkesekvensreferanse.startposisjon xml_real64, lenkesekvens.Lenkesekvensreferanse.sluttposisjon xml_real64, typeVeg xml_buffer, detaljnivå xml_buffer, konnekteringslenke xml_boolean, veglenkeadresse.Veglenkeadresse.adressekode xml_int64, veglenkeadresse.Veglenkeadresse.adressenavn xml_buffer, veglenkeadresse.Veglenkeadresse.sideveg xml_buffer, vegsystemreferanse.Vegsystemreferanse.vegsystem.Vegsystem.vegkategori xml_buffer,
      vegsystemreferanse.Vegsystemreferanse.vegsystem.Vegsystem.fase xml_buffer, vegsystemreferanse.Vegsystemreferanse.vegsystem.Vegsystem.vegnummer xml_int64, vegsystemreferanse.Vegsystemreferanse.vegstrekning.Vegstrekning.strekningNummer xml_int64, vegsystemreferanse.Vegsystemreferanse.vegstrekning.Vegstrekning.delstrekningNummer xml_int64, vegsystemreferanse.Vegsystemreferanse.vegstrekning.Vegstrekning.fraMeter xml_int64, vegsystemreferanse.Vegsystemreferanse.vegstrekning.Vegstrekning.tilMeter xml_int64, vegsystemreferanse.Vegsystemreferanse.vegstrekning.Vegstrekning.adskilteLøp xml_buffer, vegsystemreferanse.Vegsystemreferanse.vegstrekning.Vegstrekning.adskilteLøpNummer xml_buffer, vegsystemreferanse.Vegsystemreferanse.sideanlegg.Sideanlegg.sideanleggsdel xml_int64, vegsystemreferanse.Vegsystemreferanse.sideanlegg.Sideanlegg.fraMeter xml_int64, vegsystemreferanse.Vegsystemreferanse.sideanlegg.Sideanlegg.tilMeter xml_int64, vegsystemreferanse.Vegsystemreferanse.kryssystem.Kryssystem.kryssdel xml_int64, vegsystemreferanse.Vegsystemreferanse.kryssystem.Kryssystem.fraMeter xml_int64, vegsystemreferanse.Vegsystemreferanse.kryssystem.Kryssystem.tilMeter xml_int64, vegsystemreferanse.Vegsystemreferanse.referanseretning xml_buffer, feltoversikt xml_buffer, senterlinje xml_geometry
    -> ListExploder
Vegsperring (reader GML_4)
    attributes: identifikasjon.Identifikasjon.lokalId xml_buffer, identifikasjon.Identifikasjon.navnerom xml_buffer, identifikasjon.Identifikasjon.versjonId xml_buffer, oppdateringsdato xml_datetime, type xml_buffer, funksjon xml_buffer, gjeldertidsrom xml_buffer, merknad xml_buffer, eier xml_buffer, posisjon xml_geometry, lineærPosisjon.LineærPosisjonPunkt.felt xml_buffer, lineærPosisjon.LineærPosisjonPunkt.sideposisjon xml_buffer, lineærPosisjon.LineærPosisjonPunkt.høydeposisjon xml_buffer, lineærPosisjon.LineærPosisjonPunkt.posisjon xml_real64
    -> ListExploder
VærutsattVeg (reader GML_4)
    attributes: identifikasjon.Identifikasjon.lokalId xml_buffer, identifikasjon.Identifikasjon.navnerom xml_buffer, identifikasjon.Identifikasjon.versjonId xml_buffer, oppdateringsdato xml_datetime, navn xml_buffer, høyfjellsstrekning xml_buffer, stedligBeredskap xml_buffer, snødybde xml_int64, antallStengteDøgn xml_int64, vinterstengt_FraDato xml_buffer, vinterstengt_TilDato xml_buffer, nattestengt_FraDato xml_buffer, nattestengt_TilDato xml_buffer, avgrensaVinterdriftFraDato xml_buffer, avgrensaVinterdriftTilDato xml_buffer, hovedproblem xml_buffer, gjentakelsesintervall xml_buffer, terskelverdi xml_buffer, kilde xml_buffer, tilleggsinformasjon xml_buffer, senterlinje xml_geometry, lineærPosisjon{}.LineærPosisjonStrekning.felt xml_buffer, lineærPosisjon{}.LineærPosisjonStrekning.sideposisjon xml_buffer, lineærPosisjon{}.LineærPosisjonStrekning.høydeposisjon xml_buffer, lineærPosisjon{}.LineærPosisjonStrekning.fraPosisjon xml_real64, lineærPosisjon{}.LineærPosisjonStrekning.tilPosisjon xml_real64
    -> ListExploder
Note: Pakker ut liste for lineærPosisjon
ListExploder
    ATTR_ACCUM_MODE = Merge Incoming List
    ATTR_CONFLICT_RES = Use Incoming List
    INDEX_ATTR = _element_index
    LIST_ATTR = lineærPosisjon{}
    ELEMENTS -> BulkAttributeRenamer_2
    <REJECTED> -> BulkAttributeRenamer_2
Note: Fjerner eventuelt gjenværende lineærPosisjon-prefikser
BulkAttributeRenamer_2
    ATTRCHOICE = All Attributes
    CASE_DISP = YES
    MODE_CHOICE = RENAME
    PATTERN_ACTION_DISP = REMOVEPREFIX
    REPLACE_STR = lineærPosisjon.
    -> AttributeExposer
AttributeExposer
    ATTR_LIST = fme_feature_type
    -> SchemaMapper_2
    -> BulkAttributeRenamer
Note: Mapper attributtnavn til SOSI-navn
SchemaMapper_2 [off]
    CSV2_CASE_SENSITIVE_FIELD_NAMES = Yes
    CSV2_DATA_START_LINE = 2
    CSV2_DELIMITER = ;
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_SKIPPED_LINES = No
    CSV2_SCAN_ADDITIONAL_FIELDS = No
    CSV2_SCAN_MAX_ROWS = 1000
    CSV2_SCAN_TYPES = No
    CSV2_SKIP_DUPLICATE_DELIMITERS = No
    CSV2_TRIM_FIELD_NAME_QUALIFIERS = Yes
    CSV2_TRIM_FIELD_VALUE_QUALIFIERS = Yes
    CSV2_USE_CUSTOM_SCHEMA = NO
    DATASET = C:\DATA\GitHub\NVDBGML\XSD\NVDB\fkbvn\fkbvn_ptSOSIMapping.csv
    FORMAT = CSV2
    IDXDESTATTR = fme_feature_type
    IDXDESTCOL = ""
    IDXSOURCEATTR = fme_feature_type
    IDXSOURCECOL = ""
    MAP_ATTRS = name ptid $(FME_ASC_16)
    MATCH_ATTRS = ft_attr ftid
    ROW_ID_ATTR = _schemamapper_row_ids
    TABLE = CSV
    MAPPED -> BulkAttributeRenamer
Veglenke (reader GML_6)
    attributes: identifikasjon.Identifikasjon.lokalId xml_buffer, identifikasjon.Identifikasjon.navnerom xml_buffer, identifikasjon.Identifikasjon.versjonId xml_buffer, oppdateringsdato xml_datetime, datafangstdato xml_date, verifiseringsdato xml_date, kommunenummer xml_buffer, kommunenummer.codeSpace xml_buffer, kvalitet.Posisjonskvalitet.målemetode xml_buffer, kvalitet.Posisjonskvalitet.målemetode.codeSpace xml_buffer, kvalitet.Posisjonskvalitet.nøyaktighet xml_int64, kvalitet.Posisjonskvalitet.synbarhet xml_buffer, kvalitet.Posisjonskvalitet.målemetodeHøyde xml_buffer, kvalitet.Posisjonskvalitet.målemetodeHøyde.codeSpace xml_buffer, kvalitet.Posisjonskvalitet.nøyaktighetHøyde xml_int64, kvalitet.Posisjonskvalitet.maksimaltAvvik xml_int64, medium xml_buffer, standardLRM xml_buffer, lenkesekvens.Lenkesekvensreferanse.identifikasjon.Identifikasjon.lokalId xml_buffer, lenkesekvens.Lenkesekvensreferanse.identifikasjon.Identifikasjon.navnerom xml_buffer, lenkesekvens.Lenkesekvensreferanse.identifikasjon.Identifikasjon.versjonId xml_buffer, lenkesekvens.Lenkesekvensreferanse.startposisjon xml_real64, lenkesekvens.Lenkesekvensreferanse.sluttposisjon xml_real64, typeVeg xml_buffer, detaljnivå xml_buffer, konnekteringslenke xml_boolean, veglenkeadresse.Veglenkeadresse.adressekode xml_int64, veglenkeadresse.Veglenkeadresse.adressenavn xml_buffer, veglenkeadresse.Veglenkeadresse.sideveg xml_buffer, vegsystemreferanse.Vegsystemreferanse.vegsystem.Vegsystem.vegkategori xml_buffer,
      vegsystemreferanse.Vegsystemreferanse.vegsystem.Vegsystem.fase xml_buffer, vegsystemreferanse.Vegsystemreferanse.vegsystem.Vegsystem.vegnummer xml_int64, vegsystemreferanse.Vegsystemreferanse.vegstrekning.Vegstrekning.strekningNummer xml_int64, vegsystemreferanse.Vegsystemreferanse.vegstrekning.Vegstrekning.delstrekningNummer xml_int64, vegsystemreferanse.Vegsystemreferanse.vegstrekning.Vegstrekning.fraMeter xml_int64, vegsystemreferanse.Vegsystemreferanse.vegstrekning.Vegstrekning.tilMeter xml_int64, vegsystemreferanse.Vegsystemreferanse.vegstrekning.Vegstrekning.adskilteLøp xml_buffer, vegsystemreferanse.Vegsystemreferanse.vegstrekning.Vegstrekning.adskilteLøpNummer xml_buffer, vegsystemreferanse.Vegsystemreferanse.sideanlegg.Sideanlegg.sideanleggsdel xml_int64, vegsystemreferanse.Vegsystemreferanse.sideanlegg.Sideanlegg.fraMeter xml_int64, vegsystemreferanse.Vegsystemreferanse.sideanlegg.Sideanlegg.tilMeter xml_int64, vegsystemreferanse.Vegsystemreferanse.kryssystem.Kryssystem.kryssdel xml_int64, vegsystemreferanse.Vegsystemreferanse.kryssystem.Kryssystem.fraMeter xml_int64, vegsystemreferanse.Vegsystemreferanse.kryssystem.Kryssystem.tilMeter xml_int64, vegsystemreferanse.Vegsystemreferanse.referanseretning xml_buffer, feltoversikt xml_buffer, senterlinje xml_geometry
    -> BulkAttributeRenamer
    -> Veglenke
Veglenke: Inspector
Note: Setter alle attributtnavn til store bokstaver
BulkAttributeRenamer
    ATTRCHOICE = All Attributes
    CASE_CHANGE_TYPE = upper
    MODE_CHOICE = RENAME
    PATTERN_ACTION_DISP = CASECHANGE
    -> AttributeManager
Note: Individuelle endringer for en del attributter
AttributeManager
    ATTR_TABLE:
      REMOVE GML_PARENT_ID
      REMOVE GML_PARENT_PROPERTY
      REMOVE GML_ID
      RENAME_SET_VALUE IDENTIFIKASJON.IDENTIFIKASJON.LOKALID > IDENT.LOKALID
      RENAME_SET_VALUE IDENTIFIKASJON.IDENTIFIKASJON.NAVNEROM > IDENT.NAVNEROM
      RENAME_SET_VALUE IDENTIFIKASJON.IDENTIFIKASJON.VERSJONID > IDENT.VERSJONID
      RENAME_SET_VALUE KVALITET.POSISJONSKVALITET.MÅLEMETODE > KVALITET.MÅLEMETODE
      RENAME_SET_VALUE KVALITET.POSISJONSKVALITET.NØYAKTIGHET > KVALITET.NØYAKTIGHET
      RENAME_SET_VALUE KVALITET.POSISJONSKVALITET.SYNBARHET > KVALITET.SYNBARHET
      RENAME_SET_VALUE KVALITET.POSISJONSKVALITET.MÅLEMETODEHØYDE > KVALITET.MÅLEMETODEHØYDE
      RENAME_SET_VALUE KVALITET.POSISJONSKVALITET.NØYAKTIGHETHØYDE > KVALITET.NØYAKTIGHETHØYDE
      RENAME_SET_VALUE KVALITET.POSISJONSKVALITET.MAKSIMALTAVVIK > KVALITET.MAKSIMALTAVVIK
      REMOVE STANDARDLRM
      RENAME_SET_VALUE DETALJNIVÅ > VEGDETALJNIVÅ
      SET_TO KONNEKTERINGSLENKE = FME_CONDITIONAL:DEFAULT_VALUE'_FME_NO_OP_'BOOL_OP;OR;COMPOSITE_TEST;<Unused>;TEST @Value(KONNEKTERINGSLENKE) = true'JA'BOOL_OP;OR;COMPOSITE_TEST;<Unused>;TEST @Value(KONNEKTERINGSLENKE) = false'NEI'FME_NUM_CONDITIONS3___
      RENAME_SET_VALUE VEGLENKEADRESSE.VEGLENKEADRESSE.ADRESSEKODE > VEGLENKEADRESSE.ADRESSEKODE
      RENAME_SET_VALUE VEGLENKEADRESSE.VEGLENKEADRESSE.ADRESSENAVN > VEGLENKEADRESSE.ADRESSENAVN
      RENAME_SET_VALUE VEGLENKEADRESSE.VEGLENKEADRESSE.SIDEVEG > VEGLENKEADRESSE.SIDEVEG = FME_CONDITIONAL:DEFAULT_VALUE'_FME_NO_OP_'BOOL_OP;OR;COMPOSITE_TEST;<Unused>;TEST @Value(VEGLENKEADRESSE.SIDEVEG) = true'JA'BOOL_OP;OR;COMPOSITE_TEST;<Unused>;TEST @Value(VEGLENKEADRESSE.SIDEVEG) = false'NEI'FME_NUM_CONDITIONS3___
      REMOVE SENTERLINJE
      REMOVE _SCHEMAMAPPER_ROW_IDS
      RENAME_SET_VALUE LINEÆRPOSISJONSTREKNING.LENKESEKVENS.IDENTIFIKASJON.LOKALID > LRPOSISJON.LENKESEKVENS.IDENT.LOKALID
      RENAME_SET_VALUE LINEÆRPOSISJONSTREKNING.LENKESEKVENS.IDENTIFIKASJON.NAVNEROM > LRPOSISJON.LENKESEKVENS.IDENT.NAVNEROM
      RENAME_SET_VALUE LINEÆRPOSISJONSTREKNING.LENKESEKVENS.IDENTIFIKASJON.VERSJONID > LRPOSISJON.LENKESEKVENS.IDENT.VERSJONID
      RENAME_SET_VALUE LINEÆRPOSISJONSTREKNING.LINEÆRREFERANSEMETODE > LRPOSISJON.LRLRM
      RENAME_SET_VALUE LINEÆRPOSISJONSTREKNING.RETNING > LRPOSISJON.RETNING
      RENAME_SET_VALUE LINEÆRPOSISJONSTREKNING.FRAPOSISJON > LRPOSISJON.LRFRAPOSISJON
      RENAME_SET_VALUE LINEÆRPOSISJONSTREKNING.TILPOSISJON > LRPOSISJON.LRTILPOSISJON
      REMOVE _ELEMENT_INDEX
      RENAME_SET_VALUE VARETRANSPORTHVERDAGULØRDAGPERIODE1FRAKL > VARETRANSPORT_HVERDAG_1_FRA
      RENAME_SET_VALUE VARETRANSPORTHVERDAGULØRDAGPERIODE1TILKL > VARETRANSPORT_HVERDAG_1_TIL
      RENAME_SET_VALUE VARETRANSPORTHVERDAGULØRDAGPERIODE2FRAKL > VARETRANSPORT_HVERDAG_2_FRA
      RENAME_SET_VALUE VARETRANSPORTHVERDAGULØRDAGPERIODE2TILKL > VARETRANSPORT_HVERDAG_2_TIL
      RENAME_SET_VALUE VARETRANSPORTLØRDAGFRA > VARETRANSPORT_LØRDAG_FRA
      RENAME_SET_VALUE VARETRANSPORTLØRDAGTIL > VARETRANSPORT_LØRDAG_TIL
      RENAME_SET_VALUE KJØRINGTILEIENDOMMENETILLATT > KJØRING_TIL_EIENDOM_TILLAT
      RENAME_SET_VALUE LINEÆRPOSISJONPUNKT.LENKESEKVENS.IDENTIFIKASJON.LOKALID > LRPOSISJON.LENKESEKVENS.IDENT.LOKALID
      RENAME_SET_VALUE LINEÆRPOSISJONPUNKT.LENKESEKVENS.IDENTIFIKASJON.NAVNEROM > LRPOSISJON.LENKESEKVENS.IDENT.NAVNEROM
      RENAME_SET_VALUE LINEÆRPOSISJONPUNKT.LENKESEKVENS.IDENTIFIKASJON.VERSJONID > LRPOSISJON.LENKESEKVENS.IDENT.VERSJONID
      RENAME_SET_VALUE LINEÆRPOSISJONPUNKT.LINEÆRREFERANSEMETODE > LRPOSISJON.LRLRM
      RENAME_SET_VALUE LINEÆRPOSISJONPUNKT.POSISJON > LRPOSISJON.LRPUNKTPOSISJON
      RENAME_SET_VALUE SVINGEFORBUDFRA.LINEÆRPOSISJONPUNKT.LENKESEKVENS.IDENTIFIKASJON.LOKALID > SVINGEFORBUDFRA.LRPOSISJON.LENKESEKVENS.IDENT.LOKALID
      RENAME_SET_VALUE SVINGEFORBUDFRA.LINEÆRPOSISJONPUNKT.LENKESEKVENS.IDENTIFIKASJON.NAVNEROM > SVINGEFORBUDFRA.LRPOSISJON.LENKESEKVENS.IDENT.NAVNEROM
      RENAME_SET_VALUE SVINGEFORBUDFRA.LINEÆRPOSISJONPUNKT.LENKESEKVENS.IDENTIFIKASJON.VERSJONID > SVINGEFORBUDFRA.LRPOSISJON.LENKESEKVENS.IDENT.VERSJONID
      RENAME_SET_VALUE SVINGEFORBUDFRA.LINEÆRPOSISJONPUNKT.LINEÆRREFERANSEMETODE > SVINGEFORBUDFRA.LRPOSISJON.LRLRM
      RENAME_SET_VALUE SVINGEFORBUDFRA.LINEÆRPOSISJONPUNKT.POSISJON > SVINGEFORBUDFRA.LRPOSISJON.LRPUNKTPOSISJON
      RENAME_SET_VALUE SVINGEFORBUDTIL.LINEÆRPOSISJONPUNKT.LENKESEKVENS.IDENTIFIKASJON.LOKALID > SVINGEFORBUDTIL.LRPOSISJON.LENKESEKVENS.IDENT.LOKALID
      RENAME_SET_VALUE SVINGEFORBUDTIL.LINEÆRPOSISJONPUNKT.LENKESEKVENS.IDENTIFIKASJON.NAVNEROM > SVINGEFORBUDTIL.LRPOSISJON.LENKESEKVENS.IDENT.NAVNEROM
      RENAME_SET_VALUE SVINGEFORBUDTIL.LINEÆRPOSISJONPUNKT.LENKESEKVENS.IDENTIFIKASJON.VERSJONID > SVINGEFORBUDTIL.LRPOSISJON.LENKESEKVENS.IDENT.VERSJONID
      RENAME_SET_VALUE SVINGEFORBUDTIL.LINEÆRPOSISJONPUNKT.LINEÆRREFERANSEMETODE > SVINGEFORBUDTIL.LRPOSISJON.LRLRM
      RENAME_SET_VALUE SVINGEFORBUDTIL.LINEÆRPOSISJONPUNKT.POSISJON > SVINGEFORBUDTIL.LRPOSISJON.LRPUNKTPOSISJON
      SET_TO LRPOSISJON.LRLRM = FME_CONDITIONAL:DEFAULT_VALUE'_FME_NO_OP_'BOOL_OP;OR;COMPOSITE_TEST;<Unused>;TEST @Value(LRPOSISJON.LRLRM) = metrering'1'BOOL_OP;OR;COMPOSITE_TEST;<Unused>;TEST @Value(LRPOSISJON.LRLRM) = kilometrering'2'BOOL_OP;OR;COMPOSITE_TEST;<Unused>;TEST @Value(LRPOSISJON.LRLRM) = normalisert'3'BOOL_OP;OR;COMPOSITE_TEST;<Unused>;TEST @Value(LRPOSISJON.LRLRM) = prosent'5'FME_NUM_CONDITIONS5___
      RENAME_SET_VALUE KOMMUNENUMMER > KOMM
      RENAME_SET_VALUE LENKESEKVENS.LENKESEKVENSREFERANSE.IDENTIFIKASJON.IDENTIFIKASJON.LOKALID > LENKESEKVENS.IDENT.LOKALID
      RENAME_SET_VALUE LENKESEKVENS.LENKESEKVENSREFERANSE.IDENTIFIKASJON.IDENTIFIKASJON.NAVNEROM > LENKESEKVENS.IDENT.NAVNEROM
      RENAME_SET_VALUE LENKESEKVENS.LENKESEKVENSREFERANSE.IDENTIFIKASJON.IDENTIFIKASJON.VERSJONID > LENKESEKVENS.IDENT.VERSJONID
      RENAME_SET_VALUE LENKESEKVENS.LENKESEKVENSREFERANSE.STARTPOSISJON > LRSTARTVERDI
      RENAME_SET_VALUE LENKESEKVENS.LENKESEKVENSREFERANSE.SLUTTPOSISJON > LRSLUTTVERDI
      RENAME_SET_VALUE OPPDATERINGSDATO
      RENAME_SET_VALUE VEDTAKSNUMMER
      RENAME_SET_VALUE GYLDIGFRADATO
      RENAME_SET_VALUE ARKIVNUMMER
      RENAME_SET_VALUE VEGSYSTEMREFERANSE.VEGSYSTEMREFERANSE.VEGSYSTEM.VEGSYSTEM.VEGKATEGORI > VEGSYSTEMREFERANSE.VEGSYSTEM.VEGKATEGORI
      RENAME_SET_VALUE VEGSYSTEMREFERANSE.VEGSYSTEMREFERANSE.VEGSYSTEM.VEGSYSTEM.FASE > VEGSYSTEMREFERANSE.VEGSYSTEM.FASE
      RENAME_SET_VALUE VEGSYSTEMREFERANSE.VEGSYSTEMREFERANSE.VEGSYSTEM.VEGSYSTEM.VEGNUMMER > VEGSYSTEMREFERANSE.VEGSYSTEM.VEGNUMMER
      RENAME_SET_VALUE VEGSYSTEMREFERANSE.VEGSYSTEMREFERANSE.VEGSTREKNING.VEGSTREKNING.STREKNINGNUMMER > VEGSYSTEMREFERANSE.VEGSTREKNING.STREKNINGNUMMER
      RENAME_SET_VALUE VEGSYSTEMREFERANSE.VEGSYSTEMREFERANSE.VEGSTREKNING.VEGSTREKNING.DELSTREKNINGNUMMER > VEGSYSTEMREFERANSE.VEGSTREKNING.DELSTREKNINGNUMMER
      RENAME_SET_VALUE VEGSYSTEMREFERANSE.VEGSYSTEMREFERANSE.VEGSTREKNING.VEGSTREKNING.FRAMETER > VEGSYSTEMREFERANSE.VEGSTREKNING.FRAMETER
      RENAME_SET_VALUE VEGSYSTEMREFERANSE.VEGSYSTEMREFERANSE.VEGSTREKNING.VEGSTREKNING.TILMETER > VEGSYSTEMREFERANSE.VEGSTREKNING.TILMETER
      RENAME_SET_VALUE VEGSYSTEMREFERANSE.VEGSYSTEMREFERANSE.VEGSTREKNING.VEGSTREKNING.ADSKILTELØP > VEGSYSTEMREFERANSE.VEGSTREKNING.ADSKILTELØP
      RENAME_SET_VALUE VEGSYSTEMREFERANSE.VEGSYSTEMREFERANSE.VEGSTREKNING.VEGSTREKNING.ADSKILTELØPNUMMER > VEGSYSTEMREFERANSE.VEGSTREKNING.ADSKILTELØPNUMMER
      RENAME_SET_VALUE VEGSYSTEMREFERANSE.VEGSYSTEMREFERANSE.SIDEANLEGG.SIDEANLEGG.SIDEANLEGGSDEL > VEGSYSTEMREFERANSE.SIDEANLEGG.SIDEANLEGGSDEL
      RENAME_SET_VALUE VEGSYSTEMREFERANSE.VEGSYSTEMREFERANSE.SIDEANLEGG.SIDEANLEGG.FRAMETER > VEGSYSTEMREFERANSE.SIDEANLEGG.FRAMETER
      RENAME_SET_VALUE VEGSYSTEMREFERANSE.VEGSYSTEMREFERANSE.SIDEANLEGG.SIDEANLEGG.TILMETER > VEGSYSTEMREFERANSE.SIDEANLEGG.TILMETER
      RENAME_SET_VALUE VEGSYSTEMREFERANSE.VEGSYSTEMREFERANSE.KRYSSYSTEM.KRYSSYSTEM.KRYSSDEL > VEGSYSTEMREFERANSE.KRYSSYSTEM.KRYSSDEL
      RENAME_SET_VALUE VEGSYSTEMREFERANSE.VEGSYSTEMREFERANSE.KRYSSYSTEM.KRYSSYSTEM.FRAMETER > VEGSYSTEMREFERANSE.KRYSSYSTEM.FRAMETER
      RENAME_SET_VALUE VEGSYSTEMREFERANSE.VEGSYSTEMREFERANSE.KRYSSYSTEM.KRYSSYSTEM.TILMETER > VEGSYSTEMREFERANSE.KRYSSYSTEM.TILMETER
      RENAME_SET_VALUE VEGSYSTEMREFERANSE.VEGSYSTEMREFERANSE.REFERANSERETNING > VEGSYSTEMREFERANSE.REFERANSERETNING
    -> DateFormatter
Note: Formaterer datoer
DateFormatter
    DATE_ATTR = DATAFANGSTDATO
    FMT = %Y%m%d
    INVALID_DATE_VALUE = _FME_NO_OP_
    SRCFMT = Unknown - Automatic Detection
    -> Sampler_2
    -> Veglenke (writer GDMMAPPERSOSI_1)
    -> Sc [off]
    -> sosi
Sampler_2
    GROUP_BY = fme_feature_type
    RATE = 250
    SAMPLE_MODE = Yes
    SAMPLE_TYPE_LONG = Every Nth Feature
    SAMPLED -> Veglenke (writer GDMMAPPERSOSI_1)
Veglenke (writer GDMMAPPERSOSI_1)
    attributes: IDENT.LOKALID varchar(200), IDENT.NAVNEROM varchar(200), IDENT.VERSJONID varchar(200), DATAFANGSTDATO varchar(200), KVALITET.MÅLEMETODE varchar(200), KVALITET.NØYAKTIGHET varchar(200), KVALITET.SYNBARHET varchar(200), KVALITET.MÅLEMETODEHØYDE varchar(200), KVALITET.NØYAKTIGHETHØYDE varchar(200), KVALITET.MAKSIMALTAVVIK varchar(200), MEDIUM varchar(200), VEGDETALJNIVÅ varchar(200), FELTOVERSIKT varchar(200), KONNEKTERINGSLENKE varchar(200), TYPEVEG varchar(200), VEGLENKEADRESSE.ADRESSEKODE varchar(200), VEGLENKEADRESSE.ADRESSENAVN varchar(200), VEGLENKEADRESSE.SIDEVEG varchar(200), FARTSGRENSEVERDI varchar(200), LRPOSISJON.LRFRAPOSISJON varchar(200), LRPOSISJON.LRTILPOSISJON varchar(200), VEGKLASSE varchar(200), VARETRANSPORT_HVERDAG_1_FRA varchar(200), VARETRANSPORT_HVERDAG_1_TIL varchar(200), VARETRANSPORT_HVERDAG_2_FRA varchar(200), VARETRANSPORT_HVERDAG_2_TIL varchar(200), KJØRING_TIL_EIENDOM_TILLAT varchar(200), KLASSELANDBRUKSVEG varchar(200), TYPEJERNBANEKRYSSING varchar(200), POSISJON varchar(200),
      LRPOSISJON.LRPUNKTPOSISJON varchar(200), HØYFJELLSSTREKNING varchar(200), VINTERSTENGT_FRADATO varchar(200), VINTERSTENGT_TILDATO varchar(200), HOVEDPROBLEM varchar(200), SKILTAHØYDE varchar(200), TRAFIKKREGULERINGER varchar(200), TYPE varchar(200), SVINGEFORBUDFRA.LRPOSISJON.LRPUNKTPOSISJON varchar(200), SVINGEFORBUDTIL.LRPOSISJON.LRPUNKTPOSISJON varchar(200), fme_rejection_code varchar(200), LRPOSISJON.LRLRM varchar(200), KOMM varchar(200), LENKESEKVENS.IDENT.LOKALID varchar(200), LENKESEKVENS.IDENT.NAVNEROM varchar(200), LENKESEKVENS.IDENT.VERSJONID varchar(200), LRSTARTVERDI varchar(200), LRSLUTTVERDI varchar(200), GJENTAKELSESINTERVALL varchar(200), OPPDATERINGSDATO varchar(200), VEDTAKSNUMMER varchar(200), GYLDIGFRADATO varchar(200), ARKIVNUMMER varchar(200), LINEÆRPOSISJONSTREKNING.FELT varchar(200), LINEÆRPOSISJONSTREKNING.SIDEPOSISJON varchar(200), LINEÆRPOSISJONSTREKNING.HØYDEPOSISJON varchar(200), VERIFISERINGSDATO varchar(200), KOMMUNENUMMER.CODESPACE varchar(200), KVALITET.POSISJONSKVALITET.MÅLEMETODE.CODESPACE varchar(200), KVALITET.POSISJONSKVALITET.MÅLEMETODEHØYDE.CODESPACE varchar(200),
      VEGSYSTEMREFERANSE.VEGSYSTEM.VEGKATEGORI varchar(200), VEGSYSTEMREFERANSE.VEGSYSTEM.FASE varchar(200), VEGSYSTEMREFERANSE.VEGSYSTEM.VEGNUMMER varchar(200), VEGSYSTEMREFERANSE.VEGSTREKNING.STREKNINGNUMMER varchar(200), VEGSYSTEMREFERANSE.VEGSTREKNING.DELSTREKNINGNUMMER varchar(200), VEGSYSTEMREFERANSE.VEGSTREKNING.FRAMETER varchar(200), VEGSYSTEMREFERANSE.VEGSTREKNING.TILMETER varchar(200), VEGSYSTEMREFERANSE.VEGSTREKNING.ADSKILTELØP varchar(200), VEGSYSTEMREFERANSE.VEGSTREKNING.ADSKILTELØPNUMMER varchar(200), VEGSYSTEMREFERANSE.SIDEANLEGG.SIDEANLEGGSDEL varchar(200), VEGSYSTEMREFERANSE.SIDEANLEGG.FRAMETER varchar(200), VEGSYSTEMREFERANSE.SIDEANLEGG.TILMETER varchar(200), VEGSYSTEMREFERANSE.KRYSSYSTEM.KRYSSDEL varchar(200), VEGSYSTEMREFERANSE.KRYSSYSTEM.FRAMETER varchar(200), VEGSYSTEMREFERANSE.KRYSSYSTEM.TILMETER varchar(200), VEGSYSTEMREFERANSE.REFERANSERETNING varchar(200), MERKNAD varchar(200), SVINGEFORBUDFRA.LINEÆRPOSISJONPUNKT.FELT varchar(200), SVINGEFORBUDFRA.LINEÆRPOSISJONPUNKT.SIDEPOSISJON varchar(200), SVINGEFORBUDFRA.LINEÆRPOSISJONPUNKT.HØYDEPOSISJON varchar(200), SVINGEFORBUDTIL.LINEÆRPOSISJONPUNKT.FELT varchar(200), SVINGEFORBUDTIL.LINEÆRPOSISJONPUNKT.SIDEPOSISJON varchar(200), SVINGEFORBUDTIL.LINEÆRPOSISJONPUNKT.HØYDEPOSISJON varchar(200), UKEDAG varchar(200), DATOFRA varchar(200), DATOTIL varchar(200), KLOKKESLETTFRA varchar(200), KLOKKESLETTTIL varchar(200), PROSJEKTREFERANSE varchar(200), MOTORVEGTYPE varchar(200),
      SKILTNUMMER varchar(200), NAVN varchar(200), STEDLIGBEREDSKAP varchar(200), SNØDYBDE varchar(200), ANTALLSTENGTEDØGN varchar(200), NATTESTENGT_FRADATO varchar(200), NATTESTENGT_TILDATO varchar(200), AVGRENSAVINTERDRIFTFRADATO varchar(200), AVGRENSAVINTERDRIFTTILDATO varchar(200), TERSKELVERDI varchar(200), KILDE varchar(200), TILLEGGSINFORMASJON varchar(200), GJELDERTIDSROM varchar(200), VARETRANSPORTLØRDAGPERIODE1FRAKL varchar(200), VARETRANSPORTLØRDAGPERIODE1TILKL varchar(200), VARETRANSPORTLØRDAGPERIODE2FRAKL varchar(200), VARETRANSPORTLØRDAGPERIODE2TILKL varchar(200), FUNKSJON varchar(200), EIER varchar(200), LINEÆRPOSISJONPUNKT.FELT varchar(200), LINEÆRPOSISJONPUNKT.SIDEPOSISJON varchar(200), LINEÆRPOSISJONPUNKT.HØYDEPOSISJON varchar(200), TYPEHINDER varchar(200), BEREGNETHØYDE varchar(200), BREDDE varchar(200), HMINHØYREKANT varchar(200), HMINMIDT varchar(200), HMINVENSTREKANT varchar(200), MÅLEMETODE varchar(200), MÅLEDATO varchar(200)
Sc: Inspector [off]
    TACKATTRS = fme_feature_type
sosi: Inspector
