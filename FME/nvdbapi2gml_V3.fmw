FME workspace nvdbapi2gml_V3.fmw
Startup Python:
      import fme
      import fmeobjects
      from linrefTools import *

      FME_MacroValues['nvdbApiAdr'] = API

Parameters:
- kommune = 4215   # Kommunenummer
- mainFolder = C:\DATA\GIT\SOSI-Vegnett
- gmlFolder = $(mainFolder)\GML   # GML-hovedmappe
- nvdbApiAdr = https://www.vegvesen.no/nvdb/api/v3/   # NVDB API adress
- namespace = vegvesen.no.nvdb   # Namespace
- fullGmlFolder = $(gmlFolder)\kommune\$(kommune)

Writers:
- GML_1: GML to $(fullGmlFolder)

Creator
    GEOMTYPE = Geometry Object
    NUM = 1
    CREATED -> AttributeCreator
AttributeCreator
    ATTR_TABLE:
      SET_TO href = $(nvdbApiAdr)vegnett/veglenkesekvenser/segmentert?antall=5000&kommune=$(kommune)
      SET_TO omrNvn = $(kommune)
      SET_TO omr = kommune
    -> Vegnett_segmentert [_Input]
Tester_5
    BOOL_OP = OR
    TEST_CLAUSE = TEST @Value(lenkesekvens.Lenkesekvensreferanse.startposisjon) > @Value(lenkesekvens.Lenkesekvensreferanse.sluttposisjon)
    PASSED -> AttributeManager_10
    FAILED -> FeatureMerger [REQUESTOR]
AttributeManager_10
    ATTR_TABLE:
      RENAME_SET_VALUE lenkesekvens.Lenkesekvensreferanse.startposisjon > lenkesekvens.Lenkesekvensreferanse.startposisjon_old
      RENAME_SET_VALUE lenkesekvens.Lenkesekvensreferanse.sluttposisjon > lenkesekvens.Lenkesekvensreferanse.sluttposisjon_old
    -> AttributeManager_11
AttributeManager_11
    ATTR_TABLE:
      RENAME_SET_VALUE lenkesekvens.Lenkesekvensreferanse.startposisjon_old > lenkesekvens.Lenkesekvensreferanse.sluttposisjon
      RENAME_SET_VALUE lenkesekvens.Lenkesekvensreferanse.sluttposisjon_old > lenkesekvens.Lenkesekvensreferanse.startposisjon
    -> PythonCaller_2
PythonCaller_2
    PYTHONSOURCE:
      import fme
      import fmeobjects
      # Template Function interface:
      # When using this function, make sure its name is set as the value of
      # the 'Class or Function to Process Features' transformer parameter
      def processFeature(feature):
          wkt = feature.getAttribute('geometri.wkt')
          reversed_wkt = reverseWKT(wkt)
          feature.setAttribute('geometri.wkt', reversed_wkt)
    PYTHONSYMBOL = processFeature
    -> FeatureMerger [REQUESTOR]
Creator_2
    GEOMTYPE = Geometry Object
    NUM = 1
    CREATED -> AttributeCreator_5
AttributeCreator_5
    ATTR_TABLE:
      SET_TO href = $(nvdbApiAdr)vegnett/veglenkesekvenser?antall=5000&kommune=$(kommune)
      SET_TO omrNvn = $(kommune)
      SET_TO omr = kommune
    -> Vegnett [_Input]
FeatureMerger
    ATTR_ACCUM_MODE = Merge Supplier
    ATTR_CONFLICT_RES = Use Requestor
    IGNORE_NULLS = No
    JOIN_KEYS = @Value(veglenkenummer) @Value(veglenkenummer) AUTO @Value(veglenkesekvens) @Value(veglenkesekvensid) AUTO
    MERGE_TYPE = Attributes Only
    PROCESS_DUPS = NO
    REJECT_NULL_MISSING_KEYS = No
    SUPPLIERS_FIRST = No
    MERGED -> AttributeExposer_7
AttributeExposer_7
    ATTR_LIST = vegsystemreferanse.vegsystem.nummer,vegsystemreferanse.vegsystem.fase,vegsystemreferanse.vegsystem.vegkategori,vegsystemreferanse.kryssystem.fra_meter,vegsystemreferanse.kryssystem.til_meter,vegsystemreferanse.kryssystem.meter,vegsystemreferanse.kryssystem.kryssdel,vegsystemreferanse.sideanlegg.fra_meter,vegsystemreferanse.sideanlegg.til_meter,vegsystemreferanse.sideanlegg.meter,vegsystemreferanse.sideanlegg.sideanleggsdel,vegsystemreferanse.strekning.strekning,vegsystemreferanse.strekning.delstrekning,vegsystemreferanse.strekning.meter,vegsystemreferanse.strekning.fra_meter,vegsystemreferanse.strekning.til_meter,vegsystemreferanse.strekning.adskilte_løp,vegsystemreferanse.strekning.adskilte_løp_nummer,feltoversikt.felt{},vegsystemreferanse.strekning.retning,typeVeg_sosi
    -> AttributeManager_6
AttributeManager_6
    ATTR_TABLE:
      SET_TO lenkesekvensid = @Value(lenkesekvens.Lenkesekvensreferanse.identifikasjon.Identifikasjon.lokalId)
      SET_TO fraPosisjon = @Value(lenkesekvens.Lenkesekvensreferanse.startposisjon)
      SET_TO tilPosisjon = @Value(lenkesekvens.Lenkesekvensreferanse.sluttposisjon)
      SET_TO orgLenkeFraPos = @Value(lenkesekvens.Lenkesekvensreferanse.startposisjon)
      SET_TO orgLenkeTilPos = @Value(lenkesekvens.Lenkesekvensreferanse.sluttposisjon)
      RENAME_SET_VALUE vegsystemreferanse.vegsystem.nummer > vegsystemreferanse.Vegsystemreferanse.vegsystem.Vegsystem.vegnummer
      RENAME_SET_VALUE vegsystemreferanse.vegsystem.fase > vegsystemreferanse.Vegsystemreferanse.vegsystem.Vegsystem.fase
      RENAME_SET_VALUE vegsystemreferanse.vegsystem.vegkategori > vegsystemreferanse.Vegsystemreferanse.vegsystem.Vegsystem.vegkategori
      RENAME_SET_VALUE vegsystemreferanse.kryssystem.kryssdel > vegsystemreferanse.Vegsystemreferanse.kryssystem.Kryssystem.kryssdel
      RENAME_SET_VALUE vegsystemreferanse.sideanlegg.sideanleggsdel > vegsystemreferanse.Vegsystemreferanse.sideanlegg.Sideanlegg.sideanleggsdel
      RENAME_SET_VALUE vegsystemreferanse.kryssystem.fra_meter > vegsystemreferanse.Vegsystemreferanse.kryssystem.Kryssystem.fraMeter
      RENAME_SET_VALUE vegsystemreferanse.kryssystem.til_meter > vegsystemreferanse.Vegsystemreferanse.kryssystem.Kryssystem.tilMeter
      RENAME_SET_VALUE vegsystemreferanse.sideanlegg.fra_meter > vegsystemreferanse.Vegsystemreferanse.sideanlegg.Sideanlegg.fraMeter
      RENAME_SET_VALUE vegsystemreferanse.sideanlegg.til_meter > vegsystemreferanse.Vegsystemreferanse.sideanlegg.Sideanlegg.tilMeter
      RENAME_SET_VALUE vegsystemreferanse.strekning.strekning > vegsystemreferanse.Vegsystemreferanse.vegstrekning.Vegstrekning.strekningNummer
      RENAME_SET_VALUE vegsystemreferanse.strekning.delstrekning > vegsystemreferanse.Vegsystemreferanse.vegstrekning.Vegstrekning.delstrekningNummer
      RENAME_SET_VALUE vegsystemreferanse.strekning.fra_meter > vegsystemreferanse.Vegsystemreferanse.vegstrekning.Vegstrekning.fraMeter
      RENAME_SET_VALUE vegsystemreferanse.strekning.til_meter > vegsystemreferanse.Vegsystemreferanse.vegstrekning.Vegstrekning.tilMeter
      RENAME_SET_VALUE vegsystemreferanse.strekning.adskilte_løp > vegsystemreferanse.Vegsystemreferanse.vegstrekning.Vegstrekning.adskilteLøp
      RENAME_SET_VALUE vegsystemreferanse.strekning.adskilte_løp_nummer > vegsystemreferanse.Vegsystemreferanse.vegstrekning.Vegstrekning.adskilteLøpNummer
      RENAME_SET_VALUE vegsystemreferanse.strekning.retning > vegsystemreferanse.Vegsystemreferanse.referanseretning = @LowerCase(@Value(vegsystemreferanse.Vegsystemreferanse.referanseretning))
      RENAME_SET_VALUE typeVeg_sosi > typeVeg
    -> AttributeFilter_Vegfase
Note: Kun eksisterende veg
AttributeFilter_Vegfase
    ATTR_NAME = vegsystemreferanse.Vegsystemreferanse.vegsystem.Vegsystem.fase
    ATTR_VALUES = <Empty>,<Missing>,<Null>,<Unfiltered>,V,P,A
    <MISSING> -> AttributeFilter_AdskilteLøp
    V -> AttributeFilter_AdskilteLøp
AttributeFilter_AdskilteLøp
    ATTR_NAME = vegsystemreferanse.Vegsystemreferanse.vegstrekning.Vegstrekning.adskilteLøp
    ATTR_VALUES = <Empty>,<Missing>,<Null>,<Unfiltered>,Med,Mot,Nei
    <MISSING> -> InlineQuerier_vegnett_gate [vegnett]
    Med -> StringCaseChanger
    Mot -> StringCaseChanger
    Nei -> AttributeRemover_2
StringCaseChanger
    ATTRCHOICE = Selected Attributes
    ATTRLIST = vegsystemreferanse.Vegsystemreferanse.vegstrekning.Vegstrekning.adskilteLøp
    CHANGE_TYPE = lowercase
    -> InlineQuerier_vegnett_gate [vegnett]
AttributeRemover_2
    REMOVE_ATTRS = vegsystemreferanse.Vegsystemreferanse.vegstrekning.Vegstrekning.adskilteLøp
    -> InlineQuerier_vegnett_gate [vegnett]
Creator_3
    GEOMTYPE = Geometry Object
    NUM = 1
    CREATED -> AttributeSplitter
    CREATED -> AttributeManager_2
Note: 923 - Beredskapsveg; / 924 - Serviceveg; / 105 - Fartsgrense; / 721 - Fartsgrense_variabel; / 821 - Funksjonell vegklasse; / 538 - Gate; / 813 - Gågate; / 591 - Høydebegrensing; / 606 - Innkjøring forbudt; / 100 - Jernbanekryssing; / 822 - Landbruksvegklasse; / 595 - Motorveg; / 573 - Svingrestriksjon; / 856 - Trafikkregulering; / 607 - Vegsperring; / 107 - Værutsatt veg; / 532 - Vegref;
AttributeManager_2
    ATTR_TABLE = SET_TO ftIDs = 538;821;105;813;591;606;100;822;573;856;607;107;923;924;721;595
    -> AttributeSplitter
AttributeSplitter
    ATTR_NAME = ftIDs
    DELIMITER = ;
    DROP_EMPTY_PARTS = No
    LIST_NAME = _ftID
    TRIM_OPTION = Both
    -> ListExploder_2
ListExploder_2
    ATTR_ACCUM_MODE = Merge List Attributes
    ATTR_CONFLICT_RES = Use List Attribute Values
    INDEX_ATTR = _element_index
    LIST_ATTR = _ftID{}
    ELEMENTS -> AttributeCreator_2
AttributeCreator_2
    ATTR_TABLE:
      SET_TO href_tmp = $(nvdbApiAdr)vegobjekter/@Value(_ftID)?inkluder=egenskaper,geometri,metadata,lokasjon&kommune=$(kommune)
      SET_TO href = $(nvdbApiAdr)vegobjekter/@Value(_ftID)?antall=5000&&inkluder=egenskaper,geometri,metadata,lokasjon&kommune=$(kommune)
    -> Vegobjekter [_Input]
FeatureTypeFilter_2
    ATTRIBUTES = Gate,Jernbanekryssing,Vegsperring,Svingerestriksjon,Høydebegrensning,Trafikkreguleringer,Gågate,VærutsattVeg,Fartsgrense,FartsgrenseVariabel,FunksjonellVegklasse,InnkjøringForbudt,Landbruksvegklasse,Motorveg,Beredskapsveg,Serviceveg,<Unfiltered>,<Blank>
    Gate -> PythonCaller_sideveg
    Jernbanekryssing -> Junction_3
    Vegsperring -> AttributeExposer_2
    Svingerestriksjon -> PythonCaller_svingrestriksjon_2
    Høydebegrensning -> AttributeExposer_5
    Trafikkreguleringer -> AttributeExposer_6
    Gågate -> AttributeManager
    VærutsattVeg -> PythonCaller_stedlig_beredskap
    Fartsgrense -> Junction
    FartsgrenseVariabel -> Junction
    FunksjonellVegklasse -> Junction
    InnkjøringForbudt -> Junction
    Landbruksvegklasse -> Junction
    Motorveg -> Junction
    Beredskapsveg -> Junction
    Serviceveg -> Junction
InlineQuerier_vegnett_gate
    QUERY_DEF:
      merged,SELECT v.*, g.gatenavn as adressenavn, g.gatekode as adressekode, g.netelementid, g.sideveg
      FROM vegnett v
      LEFT JOIN gate g
      ON v.lenkesekvensid = g.netelementid
      AND ((v.fraPosisjon >= g.fraPos
      AND v.fraPosisjon <= g.tilPos)
      OR (v.tilPosisjon <= g.fraPos
      AND v.tilPosisjon <= g.tilPos))
      group by gml_id,FIRST
    QUERY_SCHEMA = merged,fraPosisjon,float,tilPosisjon,float,lenkesekvensid,integer,gml_id,integer,vegnett.fme_feature_content,fme_feature_content,adressenavn,text,adressekode,varchar(200),netelementid,integer,sideveg,varchar(200)
    TABLE_DEF = vegnett,fraPosisjon,float,tilPosisjon,float,lenkesekvensid,integer,gml_id,integer,gate,gatenavn,text,gatekode,varchar(200),netelementid,integer,fraPos,float,tilPos,float,sideveg,varchar(200)
    merged -> Tester
AttributeCreator_konnekteringslenke
    ATTR_TABLE = SET_TO konnekteringslenke = FME_CONDITIONAL:DEFAULT_VALUE'0'BOOL_OP;OR;COMPOSITE_TEST;<Unused>;CASE_INSENSITIVE_TEST @Value(type) CONTAINS KONNEKTERING'1'FME_NUM_CONDITIONS2___
    -> Tester_SuperFelt
AttributeManager_adresse
    ATTR_TABLE:
      RENAME_SET_VALUE adressenavn > veglenkeadresse.Veglenkeadresse.adressenavn
      RENAME_SET_VALUE adressekode > veglenkeadresse.Veglenkeadresse.adressekode
      RENAME_SET_VALUE sideveg > veglenkeadresse.Veglenkeadresse.sideveg
    -> NullAttributeMapper_2
NullAttributeMapper_2
    ATTRCHOICE = Selected Attributes
    ATTRLIST = veglenkeadresse.Veglenkeadresse.sideveg veglenkeadresse.Veglenkeadresse.adressekode veglenkeadresse.Veglenkeadresse.adressenavn
    NULL_TREATMENT = Missing
    SOURCE_ATTR_VAL = Null
    -> AttributeValueMapper_detaljnivå
Junction_3
    -> Junction_4
Junction_4
    -> PythonCaller_linref2allPunkt
Junction
    -> Junction_2
Junction_2
    -> PythonCaller_linref2all
Fagdata: Inspector [off]
    TACKATTRS = fme_feature_type
AttributeValueMapper_typeVeg
    DEFAULT_VALUE = @Value(typeVeg)
    DIRECTION = Forward (Source To Destination)
    LUT = Enkel bilveg,enkelBilveg,Gang- og sykkelveg,gangOgSykkelveg,Rundkjøring,rundkjøring,Kanalisert veg,kanalisertVeg,Gågate,gågate,Trapp,trapp,Sykkelveg,sykkelveg
    SRC = typeVeg
    VAL_ATTR = typeVeg
    -> AttributeValueMapper_detaljnivå
AttributeValueMapper_detaljnivå
    DIRECTION = Forward (Source To Destination)
    LUT = Vegtrase og kjørebane,,Kjørebane,kjørebane,Kjørefelt,kjørefelt,Vegtrase,vegtrase
    SRC = detaljnivå
    VAL_ATTR = detaljnivå
    -> NullAttributeMapper
NullAttributeMapper
    ATTRCHOICE = Selected Attributes
    ATTRLIST = detaljnivå
    NULL_TREATMENT = Missing
    SOURCE_ATTR_VAL = Null Empty
    -> AttributeFilter_detaljnivå
AttributeFilter_detaljnivå
    ATTR_NAME = detaljnivå
    ATTR_VALUES = <Empty>,<Missing>,<Null>,<Unfiltered>,kjørebane,kjørefelt,vegtrase
    <MISSING> -> PythonCaller_wktFilterNull
    kjørebane -> InlineQuerier_adresse_detaljert_vegtrase [detaljert]
    kjørefelt -> InlineQuerier_adresse_detaljert_vegtrase [detaljert]
    vegtrase -> InlineQuerier_adresse_detaljert_vegtrase [vegtrase]
InlineQuerier_adresse_detaljert_vegtrase
    QUERY_DEF:
      merged,SELECT d.*, v."veglenkeadresse.Veglenkeadresse.adressenavn" as "veglenkeadresse.Veglenkeadresse.adressenavn", v."veglenkeadresse.Veglenkeadresse.adressekode" as "veglenkeadresse.Veglenkeadresse.adressekode"
      FROM detaljert d
      LEFT JOIN vegtrase v
      ON d."superstedfesting.veglenkesekvensid" = v.veglenkesekvens
      AND ((d."superstedfesting.retning" LIKE 'med'
      AND ((d."superstedfesting.startposisjon" >= v."lenkesekvens.Lenkesekvensreferanse.startposisjon"
      AND d."superstedfesting.startposisjon" <= v."lenkesekvens.Lenkesekvensreferanse.sluttposisjon")
      OR ( d."superstedfesting.sluttposisjon" >= v."lenkesekvens.Lenkesekvensreferanse.startposisjon"
      AND d."superstedfesting.sluttposisjon" <= v."lenkesekvens.Lenkesekvensreferanse.sluttposisjon"))
      ) OR (d."superstedfesting.retning" LIKE 'mot'
      AND ((d."superstedfesting.startposisjon" >= (1-v."lenkesekvens.Lenkesekvensreferanse.startposisjon")
      AND d."superstedfesting.startposisjon" <= (1-v."lenkesekvens.Lenkesekvensreferanse.sluttposisjon"))
      OR ( d."superstedfesting.sluttposisjon" >= (1-v."lenkesekvens.Lenkesekvensreferanse.startposisjon")
      AND d."superstedfesting.sluttposisjon" <= (1-v."lenkesekvens.Lenkesekvensreferanse.sluttposisjon")))
      ))
      group by gml_id,FIRST
    QUERY_SCHEMA = merged,superstedfesting.startposisjon,float,superstedfesting.sluttposisjon,float,superstedfesting.veglenkesekvensid,integer,gml_id,integer,superstedfesting.retning,text,detaljert.fme_feature_content,fme_feature_content,veglenkeadresse.Veglenkeadresse.adressenavn,text,veglenkeadresse.Veglenkeadresse.adressekode,varchar(200)
    TABLE_DEF = detaljert,superstedfesting.startposisjon,float,superstedfesting.sluttposisjon,float,superstedfesting.veglenkesekvensid,integer,gml_id,integer,superstedfesting.retning,text,vegtrase,veglenkeadresse.Veglenkeadresse.adressenavn,text,veglenkeadresse.Veglenkeadresse.adressekode,varchar(200),veglenkesekvens,integer,lenkesekvens.Lenkesekvensreferanse.startposisjon,float,lenkesekvens.Lenkesekvensreferanse.sluttposisjon,float,veglenkeadresse.Veglenkeadresse.sideveg,varchar(200)
    merged -> PythonCaller_wktFilterNull
Veglenker: Inspector [off]
3DForcer
    KEEPZVAL = Yes
    ZVALATTR = NaN
    -> CoordinateSystemSetter
CoordinateSystemSetter
    COORDSYS = EPSG:5973
    -> FeatureWriter [Output]
    -> Vegobjekttype (writer GML_1)
FeatureWriter
    DATASET = $(gmlFolder)\kommune\$(kommune).gml
    DATASET_ATTR = _dataset
    FEATURE_TYPE_LIST_ATTR = _feature_type
    FORMAT = GML
    GML_COORDINATE_SYSTEM_GRANULARITY = DATASET
    GML_DESTINATION_DATASETTYPE_VALIDATION = Yes
    GML_INDENT_SIZE = 1
    GML_MAP_ALL_SUBSTITUTABLE_PROPERTIES = YES
    GML_MAP_COMPLEX_PROPERTIES_AS = Nested Attributes
    GML_MAP_EMBEDDED_OBJECTS_AS = ATTRIBUTES
    GML_MAP_PREDEFINED_GML_PROPERTIES = NO
    GML_PREFER_POLYGON_OVER_SURFACE = no
    GML_PRETTY_PRINT = No
    GML_PROFILE = GML Application Schema
    GML_REPLACE_TABS_WITH_SPACES = No
    GML_SUPPRESS_XSI_SCHEMALOCATION = no
    GML_TEXT_INDENT = No
    GML_USE_STYLESHEET_RESULT_AS_DATASET = no
    GML_VALIDATE_OUTPUT_DATASET = NO
    GML_XSD_DOC = $(mainFolder)\XSD\Elveg.xsd
    TOTAL_FEATURES_WRITTEN_ATTR = _total_features_written
    SUMMARY -> PythonCaller_postProcessGML
PythonCaller_postProcessGML [off]
    PYTHONSOURCE:
      import fme
      import fmeobjects
      # Template Function interface:
      # When using this function, make sure its name is set as the value of
      # the 'Class or Function to Process Features' transformer parameter
      def processFeature(feature):
          file_location = feature.getAttribute('_dataset')
          if file_location:
              postProcessGML(file_location)
    PYTHONSYMBOL = processFeature
Vegobjekttype (writer GML_1)
    attributes: id xml_char(200), geometri.wkt xml_char(200), xml_fragment xml_char(200), xml_id xml_char(200), xml_matched_element xml_char(200), xml_parent_id xml_char(200), xml_parent_child_pos xml_char(200), identifikasjon.Identifikasjon.lokalId xml_char(200), identifikasjon.Identifikasjon.versjonId xml_char(200), identifikasjon.Identifikasjon.navnerom xml_char(200), assosiasjoner{}.typeId xml_char(200), assosiasjoner{}.vegobjektId xml_char(200), assosiasjoner{}.relasjonstype xml_char(200), epsg xml_char(200), _schemamapper_row_ids xml_char(200), metadata.versjon xml_char(200), metadata.type.id xml_char(200), egenskaper.egenskap{}.id xml_char(200), egenskaper.egenskap{}.enum_id xml_char(200), egenskaper.egenskap{}.verdi xml_char(200), geometri.egengeometri xml_char(200), geometri.srid xml_char(200), lokasjon.stedfestinger.stedfesting{}.veglenkesekvens xml_char(200), lokasjon.stedfestinger.stedfesting{}.startposisjon xml_char(200), lokasjon.stedfestinger.stedfesting{}.sluttposisjon xml_char(200), geometri xml_char(200), lokasjon.stedfestinger.stedfesting{} xml_char(200), lineærPosisjon{}.LineærPosisjonStrekning.lenkesekvens.Identifikasjon.lokalId xml_char(200), lineærPosisjon{}.LineærPosisjonStrekning.lenkesekvens.Identifikasjon.navnerom xml_char(200), lineærPosisjon{}.LineærPosisjonStrekning.startposisjon xml_char(200),
      lineærPosisjon{}.LineærPosisjonStrekning.sluttposisjon xml_char(200), kommunenummer xml_char(200), oppdateringsdato xml_char(200), fase xml_char(200), typeHinder xml_char(200), trafikkreguleringer xml_char(200), stedligBeredskap xml_char(200), høyfjellsstrekning xml_char(200), svingeforbudFra.LineærPosisjonPunkt.posisjon xml_char(200), svingeforbudTil.LineærPosisjonPunkt.posisjon xml_char(200), viapunkt xml_char(200), vegtrase xml_char(200), iter xml_char(200), funksjon xml_char(200), type xml_char(200), superstedfesting.startposisjon xml_char(200), superstedfesting.sluttposisjon xml_char(200), superstedfesting.veglenkesekvensid xml_char(200), superstedfesting.retning xml_char(200), veglenkeadresse.Veglenkeadresse.adressenavn xml_char(200), veglenkeadresse.Veglenkeadresse.adressekode xml_char(200), typeVeg xml_char(200), fraPosisjon xml_char(200), tilPosisjon xml_char(200), veglenkesekvens xml_char(200), netelementid xml_char(200), startnode xml_char(200), sluttnode xml_char(200), detaljnivå xml_char(200), datafangstdato xml_char(200),
      medium xml_char(200), kvalitet.Posisjonskvalitet.synbarhet xml_char(200), lenkesekvensid xml_char(200), orgLenkeFraPos xml_char(200), orgLenkeTilPos xml_char(200), konnekteringslenke xml_char(200), lenkesekvens.Lenkesekvensreferanse.startposisjon xml_char(200), lenkesekvens.Lenkesekvensreferanse.sluttposisjon xml_char(200), lenkesekvens.Lenkesekvensreferanse.identifikasjon.Identifikasjon.lokalId xml_char(200), veglenkenummer xml_char(200), vegsystemreferanse.Vegsystemreferanse.vegsystem.Vegsystem.vegnummer xml_char(200), vegsystemreferanse.Vegsystemreferanse.vegsystem.Vegsystem.fase xml_char(200), vegsystemreferanse.Vegsystemreferanse.vegsystem.Vegsystem.vegkategori xml_char(200), vegsystemreferanse.Vegsystemreferanse.kryssystem.Kryssystem.kryssdel xml_char(200), vegsystemreferanse.Vegsystemreferanse.sideanlegg.Sideanlegg.sideanleggsdel xml_char(200), vegsystemreferanse.Vegsystemreferanse.kryssystem.Kryssystem.fraMeter xml_char(200), vegsystemreferanse.Vegsystemreferanse.kryssystem.Kryssystem.tilMeter xml_char(200), vegsystemreferanse.Vegsystemreferanse.sideanlegg.Sideanlegg.fraMeter xml_char(200), vegsystemreferanse.Vegsystemreferanse.sideanlegg.Sideanlegg.tilMeter xml_char(200), vegsystemreferanse.Vegsystemreferanse.vegstrekning.Vegstrekning.strekningNummer xml_char(200), vegsystemreferanse.Vegsystemreferanse.vegstrekning.Vegstrekning.delstrekningNummer xml_char(200), vegsystemreferanse.Vegsystemreferanse.vegstrekning.Vegstrekning.fraMeter xml_char(200), vegsystemreferanse.Vegsystemreferanse.vegstrekning.Vegstrekning.tilMeter xml_char(200), vegsystemreferanse.Vegsystemreferanse.vegstrekning.Vegstrekning.adskilteLøpNummer xml_char(200), vegsystemreferanse.kryssystem.meter xml_char(200), vegsystemreferanse.sideanlegg.meter xml_char(200), vegsystemreferanse.strekning.meter xml_char(200), vegsystemreferanse.Vegsystemreferanse.vegstrekning.Vegstrekning.adskilteLøp xml_char(200), feltoversikt.felt{} xml_char(200), veglenkeadresse.Veglenkeadresse.sideveg xml_char(200),
      feltoversikt xml_char(200), kvalitet.Posisjonskvalitet.nøyaktighetHøyde xml_char(200), kvalitet.Posisjonskvalitet.målemetode xml_char(200), kvalitet.Posisjonskvalitet.nøyaktighet xml_char(200), kvalitet.Posisjonskvalitet.maksimaltAvvik xml_char(200), veglenkesekvensid xml_char(200), vegsystemreferanse.Vegsystemreferanse.referanseretning xml_char(200), lenkesekvens.Lenkesekvensreferanse.identifikasjon.Identifikasjon.navnerom xml_char(200), standardLRM xml_char(200), _count xml_char(200), kvalitet.Posisjonskvalitet.målemetodeHøyde xml_char(200), geometri.kvalitet.målemetode xml_char(200), geometri.kvalitet.synbarhet xml_char(200), geometri.kvalitet.målemetodeHøyde xml_char(200), geometri.kvalitet.nøyaktighet xml_char(200), geometri.kvalitet.nøyaktighetHøyde xml_char(200), geometri.kvalitet.maksimaltAvvik xml_char(200), geometri.medium xml_char(200)

Bookmark: Leser og tolker XML fra NVDB-API
Vegnett_segmentert
    NESTE.HREF = @Value(href)
    OMR = kommune
    Veglenke -> Tester_5
Vegnett
    NESTE.HREF = @Value(href)
    OMR = @Value(omr)
    OMRNVN = @Value(omrNvn)
    gmlFolder = C:\wrk\SOSI-Vegnett\GML
    namespace = vegvesen.no.nvdb
    nettverk:
      ns = FME_MacroValues['namespace'] + '.nw.' + FME_MacroValues['OMR'] + '_' + FME_MacroValues['OMRNVN']
      return ns
    omr = kommune
    xsdName = elveg20-hamar
    Veglenke -> FeatureMerger [SUPPLIER]
Vegobjekter
    NESTE.HREF = @Value(href)
    -> SchemaMapper

Bookmark: Oversetter til GML-verdier og -navn
Note: Oversetter tillatte verdier til GML-verdier
SchemaMapper
    CSV2_CASE_SENSITIVE_FIELD_NAMES = Yes
    CSV2_DATA_START_LINE = 2
    CSV2_DELIMITER = ;
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_SKIPPED_LINES = No
    CSV2_SCAN_ADDITIONAL_FIELDS = No
    CSV2_SCAN_MAX_ROWS = 1000
    CSV2_SCAN_TYPES = No
    CSV2_SKIP_DUPLICATE_DELIMITERS = No
    CSV2_TRIM_FIELD_NAME_QUALIFIERS = Yes
    CSV2_TRIM_FIELD_VALUE_QUALIFIERS = Yes
    CSV2_USE_CUSTOM_SCHEMA = NO
    DATASET = $(mainFolder)\Mappingtabeller\NVDB_enMapping.csv
    FORMAT = CSV2
    IDXDESTATTR = fme_feature_type
    IDXDESTCOL = ""
    IDXSOURCEATTR = fme_feature_type
    IDXSOURCECOL = ""
    MAP_ATTRS = """""" ptid name
    MATCH_ATTRS = ptid enid
    ROW_ID_ATTR = _schemamapper_row_ids
    TABLE = CSV
    MAPPED -> SchemaMapper_2
    UNMAPPED -> SchemaMapper_2
Note: Oversetter egenskapsnavn til GML-navn
SchemaMapper_2
    CSV2_CASE_SENSITIVE_FIELD_NAMES = Yes
    CSV2_DATA_START_LINE = 2
    CSV2_DELIMITER = ;
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_SKIPPED_LINES = No
    CSV2_SCAN_ADDITIONAL_FIELDS = No
    CSV2_SCAN_MAX_ROWS = 1000
    CSV2_SCAN_TYPES = No
    CSV2_SKIP_DUPLICATE_DELIMITERS = No
    CSV2_TRIM_FIELD_NAME_QUALIFIERS = Yes
    CSV2_TRIM_FIELD_VALUE_QUALIFIERS = Yes
    CSV2_USE_CUSTOM_SCHEMA = NO
    DATASET = $(mainFolder)\Mappingtabeller\NVDB_ptMapping.csv
    FORMAT = CSV2
    IDXDESTATTR = fme_feature_type
    IDXDESTCOL = ""
    IDXSOURCEATTR = fme_feature_type
    IDXSOURCECOL = ""
    MAP_ATTRS = ptid name """"""
    MATCH_ATTRS = ft_attr ftid
    ROW_ID_ATTR = _schemamapper_row_ids
    TABLE = CSV
    MAPPED -> NullAttributeMapper_3
    UNMAPPED -> NullAttributeMapper_3
NullAttributeMapper_3
    ATTRCHOICE = All Attributes
    NULL_TREATMENT = Missing
    SOURCE_ATTR_VAL = Empty Null
    -> SchemaMapper_3
Note: Oversetter objekttypenavn til GML-navn
SchemaMapper_3
    CSV2_CASE_SENSITIVE_FIELD_NAMES = Yes
    CSV2_DATA_START_LINE = 2
    CSV2_DELIMITER = ;
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_SKIPPED_LINES = No
    CSV2_SCAN_ADDITIONAL_FIELDS = No
    CSV2_SCAN_MAX_ROWS = 1000
    CSV2_SCAN_TYPES = No
    CSV2_SKIP_DUPLICATE_DELIMITERS = No
    CSV2_TRIM_FIELD_NAME_QUALIFIERS = Yes
    CSV2_TRIM_FIELD_VALUE_QUALIFIERS = Yes
    CSV2_USE_CUSTOM_SCHEMA = NO
    DATASET = $(mainFolder)\Mappingtabeller\NVDB_ftMapping.csv
    FORMAT = CSV2
    IDXDESTATTR = fme_feature_type
    IDXDESTCOL = name
    IDXSOURCEATTR = fme_feature_type
    IDXSOURCECOL = ftid
    ROW_ID_ATTR = _schemamapper_row_ids
    TABLE = CSV
    MAPPED -> PythonCaller

Bookmark: Fase
PythonCaller
    NEW_ATTRIBUTES = fase
    PYTHONSOURCE:
      import fme
      import fmeobjects
      # Template Function interface:
      # When using this function, make sure its name is set as the value of
      # the 'Class or Function to Process Features' transformer parameter
      def processFeature(feature):
          fase = feature.getAttribute('lokasjon.vegsystemreferanser.vegsystemreferanse.vegsystem.fase')
          if fase is None:
              fase = feature.getAttribute('lokasjon.vegsystemreferanser.vegsystemreferanse{0}.vegsystem.fase')
          feature.setAttribute('fase', fase)
    PYTHONSYMBOL = processFeature
    -> AttributeFilter_Vegfase_2
Note: Kun eksisterende veg
AttributeFilter_Vegfase_2
    ATTR_NAME = fase
    ATTR_VALUES = <Empty>,<Missing>,<Null>,<Unfiltered>,V,P,A
    <EMPTY> -> AttributeExposer
    V -> AttributeExposer

Bookmark: Slette geomteri-tager slik at verdiene hentes fra FME-geometri
AttributeExposer
    ATTR_LIST = posisjon,senterlinje
    -> AttributeRemover_4
AttributeRemover_4
    REMOVE_ATTRS = senterlinje,posisjon
    -> FeatureTypeFilter_2

Bookmark: Gate
PythonCaller_sideveg
    NEW_ATTRIBUTES = sideveg
    PYTHONSOURCE:
      import fme
      import fmeobjects

      ns='vegvesen.no.nvdb' # FME_MacroValues['namespace']

      def sideveg(feature):
          i = 0
          while True:
              t = feature.getAttribute('egenskaper.egenskap{%d}.navn' % i)
              if t and t == 'Sideveg':
                      v = feature.getAttribute('egenskaper.egenskap{%d}.verdi' % i)
                      feature.setAttribute('sideveg', v)
                      break
              elif not t:
                  break
              i += 1
    PYTHONSYMBOL = sideveg
    -> ListExploder
ListExploder
    ATTR_ACCUM_MODE = Merge List Attributes
    ATTR_CONFLICT_RES = Use List Attribute Values
    INDEX_ATTR = _element_index
    LIST_ATTR = lineærPosisjon{}
    ELEMENTS -> AttributeExposer_3
AttributeExposer_3
    ATTR_LIST = LineærPosisjonStrekning.tilPosisjon,LineærPosisjonStrekning.fraPosisjon,LineærPosisjonStrekning.lenkesekvens.Identifikasjon.lokalId
    -> AttributeManager_9
AttributeManager_9
    ATTR_TABLE:
      RENAME_SET_VALUE LineærPosisjonStrekning.lenkesekvens.Identifikasjon.lokalId > netelementid
      RENAME_SET_VALUE LineærPosisjonStrekning.tilPosisjon > tilPos
      RENAME_SET_VALUE LineærPosisjonStrekning.fraPosisjon > fraPos
    -> InlineQuerier_vegnett_gate [gate]

Bookmark: Konverter meter verdier til fraMeter/tilMeter
Tester
    BOOL_OP = AND
    TEST_CLAUSE:
      TEST vegsystemreferanse.Vegsystemreferanse.vegstrekning.Vegstrekning.fraMeter ATTRIBUTE_IS_MISSING ""
      TEST vegsystemreferanse.Vegsystemreferanse.vegstrekning.Vegstrekning.tilMeter ATTRIBUTE_IS_MISSING ""
      TEST vegsystemreferanse.strekning.meter ATTRIBUTE_HAS_A_VALUE ""
    PASSED -> AttributeManager_3
    FAILED -> Tester_3
AttributeManager_3
    ATTR_TABLE:
      SET_TO vegsystemreferanse.Vegsystemreferanse.vegstrekning.Vegstrekning.fraMeter = @Value(vegsystemreferanse.strekning.meter)
      SET_TO vegsystemreferanse.Vegsystemreferanse.vegstrekning.Vegstrekning.tilMeter = @Value(vegsystemreferanse.strekning.meter)
    -> Tester_3
Tester_3
    BOOL_OP = AND
    TEST_CLAUSE:
      TEST vegsystemreferanse.Vegsystemreferanse.kryssystem.Kryssystem.tilMeter ATTRIBUTE_IS_MISSING ""
      TEST vegsystemreferanse.Vegsystemreferanse.kryssystem.Kryssystem.fraMeter ATTRIBUTE_IS_MISSING ""
      TEST vegsystemreferanse.kryssystem.meter ATTRIBUTE_HAS_A_VALUE ""
    PASSED -> AttributeManager_4
    FAILED -> Tester_4
AttributeManager_4
    ATTR_TABLE:
      SET_TO vegsystemreferanse.Vegsystemreferanse.kryssystem.Kryssystem.fraMeter = @Value(vegsystemreferanse.kryssystem.meter)
      SET_TO vegsystemreferanse.Vegsystemreferanse.kryssystem.Kryssystem.tilMeter = @Value(vegsystemreferanse.kryssystem.meter)
    -> Tester_4
Tester_4
    BOOL_OP = AND
    TEST_CLAUSE:
      TEST vegsystemreferanse.Vegsystemreferanse.sideanlegg.Sideanlegg.fraMeter ATTRIBUTE_IS_MISSING ""
      TEST vegsystemreferanse.Vegsystemreferanse.sideanlegg.Sideanlegg.tilMeter ATTRIBUTE_IS_MISSING ""
      TEST vegsystemreferanse.sideanlegg.meter ATTRIBUTE_HAS_A_VALUE ""
    PASSED -> AttributeManager_5
    FAILED -> PythonCaller_meteravrunding
AttributeManager_5
    ATTR_TABLE:
      SET_TO vegsystemreferanse.Vegsystemreferanse.sideanlegg.Sideanlegg.fraMeter = @Value(vegsystemreferanse.sideanlegg.meter)
      SET_TO vegsystemreferanse.Vegsystemreferanse.sideanlegg.Sideanlegg.tilMeter = @Value(vegsystemreferanse.sideanlegg.meter)
    -> PythonCaller_meteravrunding
PythonCaller_meteravrunding
    PYTHONSOURCE:
      import fme
      import fmeobjects


      def valueRounder(feature):
          vals = ['vegsystemreferanse.Vegsystemreferanse.kryssystem.Kryssystem.fraMeter',
              'vegsystemreferanse.Vegsystemreferanse.kryssystem.Kryssystem.tilMeter',
              'vegsystemreferanse.Vegsystemreferanse.sideanlegg.Sideanlegg.fraMeter',
              'vegsystemreferanse.Vegsystemreferanse.sideanlegg.Sideanlegg.tilMeter',
              'vegsystemreferanse.Vegsystemreferanse.vegstrekning.Vegstrekning.fraMeter',
              'vegsystemreferanse.Vegsystemreferanse.vegstrekning.Vegstrekning.tilMeter']

          for val in vals:
              v = feature.getAttribute(val)
              if v:
                  feature.setAttribute(val, round(float(v)))
    PYTHONSYMBOL = valueRounder
    -> AttributeCreator_konnekteringslenke

Bookmark: Felt
Tester_SuperFelt
    BOOL_OP = AND
    TEST_CLAUSE = TEST feltoversikt.felt{0} ATTRIBUTE_IS_MISSING ""
    PASSED -> PythonCaller_SuperFelt
    FAILED -> Tester_2
PythonCaller_SuperFelt
    PYTHONSOURCE:
      import fme
      import fmeobjects
      # Template Function interface:
      # When using this function, make sure its name is set as the value of
      # the 'Class or Function to Process Features' transformer parameter
      def processFeature(feature):
          enkelt_felt = feature.getAttribute('feltoversikt.felt')
          if enkelt_felt:
              feature.setAttribute('feltovesikt.felt{0}', enkelt_felt)
              return
          felt = feature.getAttribute('superstedfesting.kjørefelt.felt{}')
          if not felt: return
          for i, val in enumerate(felt):
              feature.setAttribute('feltoversikt.felt{%d}' % i, val)
    PYTHONSYMBOL = processFeature
    -> Tester_2
Tester_2
    BOOL_OP = OR
    TEST_CLAUSE = TEST @Value(vegsystemreferanse.Vegsystemreferanse.referanseretning) = mot
    PASSED -> PythonCaller_felt
    FAILED -> ListSorter
PythonCaller_felt
    PYTHONSOURCE:
      import fme
      import fmeobjects
      # Template Function interface:
      # When using this function, make sure its name is set as the value of
      # the 'Class or Function to Process Features' transformer parameter
      #logger = fmeobjects.FMELogFile()

      def processFeature(feature):
          felt = feature.getAttribute('feltoversikt.felt{}')
          if felt:
              felt = snuFeltListe(felt)
              #logger.logMessageString(str(felt))
          feature.setAttribute('feltoversikt.felt{}', felt)
    PYTHONSYMBOL = processFeature
    -> ListSorter
ListSorter
    ORDER = Ascending
    SRC_LIST = feltoversikt.felt{}
    TYPE = Alphabetic
    -> ListConcatenator_felt
ListConcatenator_felt
    DROP_EMPTY_PARTS = Yes
    LIST_ATTR = feltoversikt.felt{}
    SEP = #
    VAL_ATTR = feltoversikt
    -> AttributeManager_adresse

Bookmark: Vegsperring
AttributeExposer_2
    ATTR_LIST = type
    -> AttributeManager_7
AttributeManager_7
    ATTR_TABLE = SET_TO funksjon = @Value(type)
    -> AttributeValueMapper
AttributeValueMapper
    DEFAULT_VALUE = trafikkavviser
    DIRECTION = Forward (Source To Destination)
    LUT = 9975,låstSperring,9971,trafikkavviser,9972,trafikkavviser,9973,trafikkavviser,9970,trafikkavviser,9974,bussluse,11799,trafikkavviser,11800,trafikkavviser,13369,fjernstyrtSperring
    SRC = type
    VAL_ATTR = funksjon
    -> AttributeValueMapper_2
AttributeValueMapper_2
    DEFAULT_VALUE = FME_NULL_VALUE
    DIRECTION = Forward (Source To Destination)
    LUT = 9975,låstBom,9971,rørgelender,9972,steinblokk,9973,newJersey,9970,betongkjegle,9974,bussluse,11799,trafikkavviser,11800,bilsperre,13369,bomMedAutomatiskÅpner
    SRC = type
    VAL_ATTR = type
    -> NullAttributeMapper_5
NullAttributeMapper_5
    ATTRCHOICE = Selected Attributes
    ATTRLIST = type
    NULL_TREATMENT = Missing
    SOURCE_ATTR_VAL = Null
    -> PythonCaller_linref2allPunkt

Bookmark: VegrefPunkt2geom
PythonCaller_linref2allPunkt
    PYTHONSOURCE:
      import fme
      import fmeobjects
      import uuid

      logger = fmeobjects.FMELogFile()
      navnerom = 'vegvesen.no.nvdb.rls'

      class FeatureProcessor_linref2allPunkt(object):
          def __init__(self):
              pass
          def input(self,feature):
              vals = feature.getAttribute('lineærPosisjon{}.LineærPosisjonPunkt.lenkesekvens.Identifikasjon.lokalId')
              for (j, vl_id) in enumerate(vals):
                  posisjon = feature.getAttribute('lineærPosisjon{%d}.LineærPosisjonPunkt.posisjon' % j)
                  felt = feature.getAttribute('lineærPosisjon{%d}.LineærPosisjonStrekning.felt{}' % j) or []
                  #slutt = feature.getAttribute('lineærPosisjon{%d}.LineærPosisjonPunkt.tilPosisjon' % j)
                  #retning = feature.getAttribute('lineærPosisjon{%d}.LineærPosisjonPunkt.retning' % j)
                  id = feature.getAttribute('identifikasjon.Identifikasjon.lokalId')
                  #logger.logMessageString('id: %s, start: %s, slutt: %s, retning: %s' % (vl_id, start, slutt, retning))
                  lst = linref2allPunkt(vl_id, posisjon, felt)
                  #logger.logMessageString(str(len(lst)))
                  for obj in lst:
                      newF = feature.clone()
                      linpos = feature.getAttribute('lineærPosisjon{}.LineærPosisjon.Punkt.lenkesekvens.Identifikasjon.lokalId')
                      #logger.logMessageString(str(linpos))
                      if linpos:
                          for i in range(len(linpos)):
                              #print('i %d' % i)
                              #newF.removeAttribute('lineærPosisjon{%d}' % i)
                              newF.removeAttribute('lineærPosisjon.LineærPosisjonPunkt.lenkesekvens.Identifikasjon.lokalId')
                              newF.removeAttribute('lineærPosisjon.LineærPosisjonPunkt.lenkesekvens.Identifikasjon.navnerom')
                              newF.removeAttribute('lineærPosisjon.LineærPosisjonPunkt.lineærReferanseMetode')
                              newF.removeAttribute('lineærPosisjon.LineærPosisjonpunkt.punkt')
                      newId = navnerom + '_' + id + '_' + uuid.uuid4().hex[:6].upper()
                      #newId = "_".join([navnerom,str(id),str(obj['veglenkesekvens']),str(obj['posisjon']),feltstr(felt)])
                      newF.setAttribute('identifikasjon.Identifikasjon.lokalId', newId)
                      newF.setAttribute('gml_id', newId)
                      newF.setAttribute('lineærPosisjon.LineærPosisjonPunkt.lenkesekvens.Identifikasjon.lokalId', obj['veglenkesekvens'])
                      newF.setAttribute('lineærPosisjon.LineærPosisjonPunkt.lenkesekvens.Identifikasjon.navnerom', navnerom)
                      newF.setAttribute('lineærPosisjon.LineærPosisjonPunkt.posisjon', obj['posisjon'])
                      if felt: newF.setAttribute('lineærPosisjon{0}.LineærPosisjonStrekning.felt', "#".join(felt))
                      newF.setAttribute('geometri.wkt', obj['geom'].wkt) # move .wkt to start script?
                      self.pyoutput(newF)

          def close(self):
              pass
    PYTHONSYMBOL = FeatureProcessor_linref2allPunkt
    -> GeometryReplacer_3
GeometryReplacer_3
    KIND_LONG = OGC Well Known Text
    OGC_WKT_PRECISION_DISPLAY = 64-bit
    REMOVE_ATTRIBUTE = No
    SOURCE = @Value(geometri.wkt)
    -> GeometryFilter

Bookmark: Svingrestriksjon
PythonCaller_svingrestriksjon_2
    NEW_ATTRIBUTES = svingeforbudFra.LineærPosisjonPunkt.posisjon svingeforbudTil.LineærPosisjonPunkt.posisjon viapunkt vegtrase
    PYTHONSOURCE:
      import fme
      import fmeobjects

      ns='vegvesen.no.nvdb' # FME_MacroValues['namespace']

      def svingrestriksjon(feature):
          v = feature.getAttribute('egenskaper.egenskap.startpunkt.relativPosisjon')
          if v:
              feature.setAttribute('svingeforbudFra.LineærPosisjonPunkt.posisjon', v)
              feature.setAttribute('svingeforbudFra.LineærPosisjonPunkt.lineærReferanseMetode', 'normalisert')
              v = feature.getAttribute('egenskaper.egenskap.nodeid')
              if v != 'None':
                  feature.setAttribute('viapunkt', v)
              v = feature.getAttribute('egenskaper.egenskap.startpunkt.veglenkesekvensid')
              if v != 'None':
                  feature.setAttribute('svingeforbudFra.LineærPosisjonPunkt.lenkesekvens.Identifikasjon.lokalId', v)
                  feature.setAttribute('svingeforbudFra.LineærPosisjonPunkt.lenkesekvens.Identifikasjon.navnerom', ns + '.rls')
              v = feature.getAttribute('egenskaper.egenskap.sluttpunkt.relativPosisjon')
              if v != 'None':
                  feature.setAttribute('svingeforbudTil.LineærPosisjonPunkt.posisjon', v)
                  feature.setAttribute('svingeforbudTil.LineærPosisjonPunkt.lineærReferanseMetode', 'normalisert')
                  v = feature.getAttribute('egenskaper.egenskap.sluttpunkt.veglenkesekvensid')
                  if v != 'None':
                      feature.setAttribute('svingeforbudTil.LineærPosisjonPunkt.lenkesekvens.Identifikasjon.lokalId', v)
                      feature.setAttribute('svingeforbudTil.LineærPosisjonPunkt.lenkesekvens.Identifikasjon.navnerom', ns + '.rls')
          else: # Flere egenskaper
              i = 0
              while True:
                  v = str(feature.getAttribute('egenskaper.egenskap{%d}.egenskapstype' % i))
                  w = str(feature.getAttribute('egenskaper.egenskap{%d}.navn' % i))
                  if v == 'None' and i > 0:
                      break
                  elif v == 'Stedfesting' and w == 'SvingTilknytning':
                      v = feature.getAttribute('egenskaper.egenskap{%d}.nodeid' % i)
                      if v != 'None':
                          feature.setAttribute('viapunkt', v)
                      v = feature.getAttribute('egenskaper.egenskap{%d}.startpunkt.relativPosisjon' % i)
                      if v != 'None':
                          feature.setAttribute('svingeforbudFra.LineærPosisjonPunkt.posisjon', v)
                          feature.setAttribute('svingeforbudFra.LineærPosisjonPunkt.lineærReferanseMetode', 'normalisert')
                          v = feature.getAttribute('egenskaper.egenskap{%d}.startpunkt.veglenkesekvensid' % i)
                          if v != 'None':
                              feature.setAttribute('svingeforbudFra.LineærPosisjonPunkt.lenkesekvens.Identifikasjon.lokalId', v)
                              feature.setAttribute('svingeforbudFra.LineærPosisjonPunkt.lenkesekvens.Identifikasjon.navnerom', ns + '.rls')
                      v = feature.getAttribute('egenskaper.egenskap{%d}.sluttpunkt.relativPosisjon' % i)
                      if v != 'None':
                          feature.setAttribute('svingeforbudTil.LineærPosisjonPunkt.posisjon', v)
                          feature.setAttribute('svingeforbudTil.LineærPosisjonPunkt.lineærReferanseMetode', 'normalisert')
                          v = feature.getAttribute('egenskaper.egenskap{%d}.sluttpunkt.veglenkesekvensid' % i)
                          if v != 'None':
                              feature.setAttribute('svingeforbudTil.LineærPosisjonPunkt.lenkesekvens.Identifikasjon.lokalId', v)
                              feature.setAttribute('svingeforbudTil.LineærPosisjonPunkt.lenkesekvens.Identifikasjon.navnerom', ns + '.rls')
                  i += 1
          if isVegtrase(feature.getAttribute('svingeforbudFra.LineærPosisjonPunkt.lenkesekvens.Identifikasjon.lokalId'), feature.getAttribute('svingeforbudFra.LineærPosisjonPunkt.posisjon')) \
             or isVegtrase(feature.getAttribute('svingeforbudTil.LineærPosisjonPunkt.lenkesekvens.Identifikasjon.lokalId'), feature.getAttribute('svingeforbudTil.LineærPosisjonPunkt.posisjon')):
              feature.setAttribute('vegtrase', 'yes')
          else:
              feature.setAttribute('vegtrase', 'no')
    PYTHONSYMBOL = svingrestriksjon
    -> Tester_6
Tester_6
    BOOL_OP = OR
    TEST_CLAUSE = TEST @Value(vegtrase) = yes
    PASSED -> FeatureMerger_3 [REQUESTOR]
    PASSED -> node2geom
node2geom
    VIAPUNKT = @Value(viapunkt)
    namespace = vegvesen.no.nvdb
    nvdbApiAdr = $(nvdbApiAdr)
    -> FeatureMerger_3 [SUPPLIER]
FeatureMerger_3
    ATTR_ACCUM_MODE = Merge Supplier
    ATTR_CONFLICT_RES = Use Requestor
    IGNORE_NULLS = No
    JOIN_KEYS = @Value(viapunkt) @Value(viapunkt) AUTO
    MERGE_TYPE = Attributes Only
    PROCESS_DUPS = NO
    REJECT_NULL_MISSING_KEYS = No
    SUPPLIERS_FIRST = No
    MERGED -> GeometryReplacer
GeometryReplacer
    KIND_LONG = OGC Well Known Text
    OGC_WKT_PRECISION_DISPLAY = 64-bit
    REMOVE_ATTRIBUTE = Yes
    SOURCE = @Value(geom)
    -> GeometryFilter

Bookmark: Høydebegrensing
AttributeExposer_5
    ATTR_LIST = typeHinderHøydebegrensning
    -> AttributeRenamer_2
AttributeRenamer_2
    ATTR_TABLE = RENAME_SET_DEFAULT typeHinderHøydebegrensning > typeHinder
    -> PythonCaller_linref2all

Bookmark: Trafikkreguleringer
AttributeExposer_6
    ATTR_LIST = trafikkreguleringstype
    -> AttributeRenamer
AttributeRenamer
    ATTR_TABLE = RENAME_SET_DEFAULT trafikkreguleringstype > trafikkreguleringer
    -> PythonCaller_linref2all

Bookmark: Gågate
AttributeManager
    ATTR_TABLE = SET_TO fme_feature_type = Gågatereguleringer
    -> PythonCaller_linref2all

Bookmark: Værutsattveg
PythonCaller_stedlig_beredskap
    NEW_ATTRIBUTES = stedligBeredskap
    PYTHONSOURCE:
      import fme
      import fmeobjects

      def stedligBeredskap(feature):
          n = feature.getAttribute('egenskaper.egenskap.navn')
          if n == 'Stedlig beredskap':
              v = feature.getAttribute('egenskaper.egenskap.verdi')
              feature.setAttribute('stedligBeredskap', v)
          else: # Flere egenskaper
              i = 0
              while True:
                  n = str(feature.getAttribute('egenskaper.egenskap{%d}.navn' % i))
                  if n == 'None' and i > 0:
                      break
                  elif n == 'Stedlig beredskap':
                      v = feature.getAttribute('egenskaper.egenskap{%d}.verdi' % i)
                      feature.setAttribute('stedligBeredskap', v)
                  i += 1
    PYTHONSYMBOL = stedligBeredskap
    -> AttributeExposer_4
AttributeExposer_4
    ATTR_LIST = høyfjellsstrekning
    -> NullAttributeMapper_6
NullAttributeMapper_6
    ATTRCHOICE = Selected Attributes
    ATTRLIST = høyfjellsstrekning
    NEW_VALUE = uavklart
    NULL_TREATMENT = New Value
    SOURCE_ATTR_VAL = Null Empty "Missing (Selected Attributes Only)"
    -> PythonCaller_linref2all

Bookmark: Vegref2geom
PythonCaller_linref2all
    PYTHONSOURCE:
      import fme
      import fmeobjects
      import uuid

      logger = fmeobjects.FMELogFile()
      navnerom = 'vegvesen.no.nvdb.rls'

      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor_linref2all(object):
          def __init__(self):
              pass
          def input(self,feature):
              vals = feature.getAttribute('lineærPosisjon{}.LineærPosisjonStrekning.lenkesekvens.Identifikasjon.lokalId')
              #print('vals: %s' % vals)
              for (j, vl_id) in enumerate(vals):
                  #vl_id = None
                  #vl_id = feature.getAttribute('lineærPosisjon{%d}.LineærPosisjonStrekning.lenkesekvens.Identifikasjon.lokalId' % j)
                  #print("vl_id: %s" % vl_id)
                  #if vl_id == None:
                      #break
                  start = feature.getAttribute('lineærPosisjon{%d}.LineærPosisjonStrekning.fraPosisjon' % j)
                  slutt = feature.getAttribute('lineærPosisjon{%d}.LineærPosisjonStrekning.tilPosisjon' % j)
                  retning = feature.getAttribute('lineærPosisjon{%d}.LineærPosisjonStrekning.retning' % j)
                  felt = feature.getAttribute('lineærPosisjon{%d}.LineærPosisjonStrekning.felt{}' % j) or feature.getAttribute('lineærPosisjon{%d}.LineærPosisjonStrekning.felt' % j) or []
                  id = feature.getAttribute('identifikasjon.Identifikasjon.lokalId')
                  #logger.logMessageString('id: %s, start: %s, slutt: %s, retning: %s, felt: %s' % (vl_id, start, slutt, retning, felt))
                  lst = linref2all(vl_id, start, slutt, FME_MacroValues['kommune'], retning, felt)
                  #logger.logMessageString(str(len(lst)))
                  for obj in lst:
                      newF = feature.clone()
                      linpos = feature.getAttribute('lineærPosisjon{}.LineærPosisjonStrekning.lenkesekvens.Identifikasjon.lokalId')
                      #logger.logMessageString(str(linpos))
                      if linpos:
                          for i in range(len(linpos)):
                              #print('i %d' % i)
                              #newF.removeAttribute('lineærPosisjon{%d}' % i)
                              newF.removeAttribute('lineærPosisjon{%d}.LineærPosisjonStrekning.lenkesekvens.Identifikasjon.lokalId' % i)
                              newF.removeAttribute('lineærPosisjon{%d}.LineærPosisjonStrekning.lenkesekvens.Identifikasjon.navnerom' % i)
                              newF.removeAttribute('lineærPosisjon{%d}.LineærPosisjonStrekning.lineærReferanseMetode' % i)
                              newF.removeAttribute('lineærPosisjon{%d}.LineærPosisjonStrekning.retning' % i)
                              newF.removeAttribute('lineærPosisjon{%d}.LineærPosisjonStrekning.fraPosisjon' % i)
                              newF.removeAttribute('lineærPosisjon{%d}.LineærPosisjonStrekning.tilPosisjon' % i)
                      newId = navnerom + '_' + id + '_' + uuid.uuid4().hex[:6].upper()
                      #newId = "_".join([navnerom,str(id),str(obj['veglenkesekvens']),str(obj['start']),str(obj['slutt']),feltstr(felt)])
                      newF.setAttribute('identifikasjon.Identifikasjon.lokalId', newId)
                      newF.setAttribute('gml_id', newId)
                      newF.setAttribute('lineærPosisjon{0}.LineærPosisjonStrekning.lenkesekvens.Identifikasjon.lokalId', obj['veglenkesekvens'])
                      newF.setAttribute('lineærPosisjon{0}.LineærPosisjonStrekning.lenkesekvens.Identifikasjon.navnerom', navnerom)
                      newF.setAttribute('lineærPosisjon{0}.LineærPosisjonStrekning.fraPosisjon', obj['start'])
                      newF.setAttribute('lineærPosisjon{0}.LineærPosisjonStrekning.tilPosisjon', obj['slutt'])
                      newF.setAttribute('lineærPosisjon{0}.LineærPosisjonStrekning.retning', obj['retning'])
                      if felt: newF.setAttribute('lineærPosisjon{0}.LineærPosisjonStrekning.felt', feltstr(felt))
                      newF.setAttribute('geometri.wkt', obj['geom'].wkt) # move .wkt to start script?
                      self.pyoutput(newF)

              #self.pyoutput(feature)
          def close(self):
              pass
    PYTHONSYMBOL = FeatureProcessor_linref2all
    -> GeometryReplacer_2
GeometryReplacer_2
    KIND_LONG = OGC Well Known Text
    OGC_WKT_PRECISION_DISPLAY = 64-bit
    REMOVE_ATTRIBUTE = No
    SOURCE = @Value(geometri.wkt)
    -> GeometryFilter

Bookmark: Definerer geometriegenskaper
GeometryFilter
    BREAK_AGG = No
    GEOM_PORT_NAMES = Point Line Area
    POINT -> GeometryPropertySetter
    LINE -> GeometryPropertySetter_4
    AREA -> GeometryPropertySetter_3
    <UNFILTERED> -> AttributeRemover_OUTPUT_-___Value_fme_feature_type_
GeometryPropertySetter
    GEOM_NAME_FIELD = posisjon
    OVERWRITE_CHOICE = Yes
    SETTYPE_PARAM = Geometry Name
    SET -> AttributeRemover_OUTPUT_-___Value_fme_feature_type_
GeometryPropertySetter_4
    GEOM_NAME_FIELD = senterlinje
    OVERWRITE_CHOICE = Yes
    SETTYPE_PARAM = Geometry Name
    SET -> AttributeRemover
AttributeRemover
    REMOVE_ATTRS = posisjon
    -> AttributeRemover_OUTPUT_-___Value_fme_feature_type_
GeometryPropertySetter_3
    GEOM_NAME_FIELD = område
    OVERWRITE_CHOICE = Yes
    SETTYPE_PARAM = Geometry Name
    SET -> AttributeRemover_OUTPUT_-___Value_fme_feature_type_
AttributeRemover_OUTPUT_-___Value_fme_feature_type_: Junction
    -> Fagdata
    -> 3DForcer

Bookmark: Geometri
PythonCaller_wktFilterNull
    PYTHONSOURCE:
      import fme
      import fmeobjects

      def processFeature_wktFilterNull(feature):
          wkt = feature.getAttribute('geometri.wkt')
          line = wkt2line(wkt) # filtrerer også bort -999999
          feature.setAttribute('geometri.wkt', line.wkt)
    PYTHONSYMBOL = processFeature_wktFilterNull
    -> GeometryReplacer_4
GeometryReplacer_4
    KIND_LONG = OGC Well Known Text
    OGC_WKT_PRECISION_DISPLAY = 64-bit
    REMOVE_ATTRIBUTE = No
    SOURCE = @Value(geometri.wkt)
    -> GeometryPropertySetter_2
GeometryPropertySetter_2
    GEOM_NAME_FIELD = senterlinje
    OVERWRITE_CHOICE = Yes
    SETTYPE_PARAM = Geometry Name
    SET -> Veglenker
    SET -> 3DForcer

FME custom transformer Vegnett_segmentert
Leser og tolker data fra NVDB-API

Parameters:
- NESTE.HREF = @Value(neste.href)   # neste.href
- OMR = @Value(kommune)   # omr

_Input (input)
    -> AttributeCreator
AttributeCreator
    ATTR_TABLE = SET_TO iter = 0
    -> HTTPCaller_2
Loop (input)
    -> HTTPCaller_2
HTTPCaller_2
    CONNECTION_TIMEOUT_LENGTH = 60
    CUSTOM_HEADERS = Accept;application/vnd.vegvesen.nvdb-v3-rev1+xml X-Client;Elveg 2.0
    ERROR_ATTR = _error
    FOLLOW_REDIRECTS = Yes
    HTTP_METHOD = GET
    RESPONSE_HEADER_LIST_ATTR = _headers
    SAVE_FILE = Attribute
    STATUS_CODE_ATTR = _http_status_code
    TARGET_ATTR = _url_contents
    TARGET_ATTR_ENCODING = auto-detect
    TARGET_URL = @Value(neste.href)
    TRANSFER_TIMEOUT_LENGTH = 90
    USE_COOKIES = No
    VERIFY_SSL_CERTIFICATES = Yes
    -> XMLFragmenter_2
    -> XMLFragmenter
    <REJECTED> -> Tester
Note: Deler opp i en XML pr vegobjekt
XMLFragmenter
    ATTRIBUTE_XML = _url_contents
    EMBEDDED_EXPRESSIONS = objekter/veglenkesekvens
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = No
    NEW_ATTRIBUTES = id geometri.wkt startnode sluttnode veglenkenummer
    REJECT_FEATURES_WITH_NO_FRAGMENTS = YES
    XML_SOURCE_TYPE = Attribute with XML document
    FRAGMENTS -> AttributeExposer
AttributeExposer
    ATTR_LIST = identifikasjon.Identifikasjon.navnerom,lenkesekvens.Lenkesekvensreferanse.identifikasjon.Identifikasjon.navnerom,veglenkesekvensid,identifikasjon.Identifikasjon.lokalId,lenkesekvens.Lenkesekvensreferanse.identifikasjon.Identifikasjon.lokalId,gml_id,felt,topologinivå,startposisjon,sluttposisjon,veglenkenummer,geometri.wkt,kommune
    -> Counter
Counter
    CNT_ATTR = _count
    DOMAIN = @Value(veglenkesekvensid)
    SCOPE = Global
    START = 0
    -> AttributeManager
AttributeManager
    ATTR_TABLE:
      SET_TO identifikasjon.Identifikasjon.navnerom = vegvesen.no.nvdb.rls
      SET_TO lenkesekvens.Lenkesekvensreferanse.identifikasjon.Identifikasjon.navnerom = vegvesen.no.nvdb.rls
      SET_TO identifikasjon.Identifikasjon.lokalId = @Value(veglenkesekvensid)_@Value(_count)
      SET_TO lenkesekvens.Lenkesekvensreferanse.identifikasjon.Identifikasjon.lokalId = @Value(veglenkesekvensid)
      RENAME_SET_VALUE felt > feltoversikt
      RENAME_SET_VALUE topologinivå > detaljnivå
      RENAME_SET_VALUE startposisjon > lenkesekvens.Lenkesekvensreferanse.startposisjon
      RENAME_SET_VALUE sluttposisjon > lenkesekvens.Lenkesekvensreferanse.sluttposisjon
      RENAME_SET_VALUE veglenkesekvensid > veglenkesekvens
      SET_TO fme_feature_type = Veglenke
      RENAME_SET_VALUE kommune > kommunenummer = @PadLeft(@Value(kommunenummer),4,0)
      SET_TO standardLRM = normalisert
      SET_TO gml_id = vegvesen.no.nvdb.rl.@Value(veglenkesekvens)_@Value(_count)
    -> Veglenke (output)
Veglenke (output)
XMLFragmenter_2
    ATTRIBUTE_XML = _url_contents
    EMBEDDED_EXPRESSIONS = side/metadata
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = No
    NEW_ATTRIBUTES = returnert neste.href
    REJECT_FEATURES_WITH_NO_FRAGMENTS = YES
    XML_SOURCE_TYPE = Attribute with XML document
    FRAGMENTS -> TestFilter
TestFilter
    DEFAULT_VALUE = <UNFILTERED>
    TEST_LIST = BOOL_OP,OR,COMPOSITE_TEST,<Unused>,TEST_CLAUSE,"TEST @Value(returnert) != 0",Flere
    Flere -> Loop (output)
Tester
    BOOL_OP = OR
    TEST_CLAUSE = TEST @Value(iter) < 5
    PASSED -> AttributeManager_2
    FAILED -> Terminator
AttributeManager_2
    ATTR_TABLE = SET_TO iter = @int(@Value(iter))+1
    -> Decelerator
Decelerator
    DECEL_TYPE = Per Feature Delay
    DELAY = 15
    -> Loop (output)
Loop (output)
Terminator
    MESSAGE = Translation Terminated

FME custom transformer Segments_2
Creates a list of segments with RoladLinkID, from meassure and to-meassure from an overlay between event tables

Parameters:
- RoadLinkID =   # RoadLinkID Attribute
- FromVal = fra_meter   # From meassure Attribute
- ToVal = til_meter   # To meassure Attribute

Event_Tables (input)
    -> AttributeCreator_2
Note: Unique list of breakpoints
Breakpoint_List: BreakpointList
    FROMVAL = @Value(FromVal)
    ROADLINKID = @Value(RoadLinkID)
    TOVAL = @Value(ToVal)
    __COMPOUND_PARAMETERS = -
    Breakpoint_List -> ListElementCounter
ListElementCounter
    CNT_ATTR = _element_count
    LIST_NAME = _Bp_list{}
    -> ExpressionEvaluator
ExpressionEvaluator
    EXPRESSION = @Value(_element_count)-1
    VAL_ATTR = _maxIdx
    -> AttributeCreator
AttributeCreator
    ATTR_LIST = _idx,0
    -> UniqeSegments [BREAKPOINTLIST]
Note: Unique table of segments
UniqeSegments
    __COMPOUND_PARAMETERS = -
    Unique_Segments -> StringConcatenator
Note: Segment ID
StringConcatenator
    PARM_LINE = fme_basicstring:18%1%15%1%13:@Value(RoadLinkID)_@Value(FromVal)_@Value(ToVal)
    VAL_ATTR = _SegId
    -> Unique_Segment_List (output)
Unique_Segment_List (output)

Bookmark: Link ID and meassure attributes
AttributeCreator_2
    ATTR_LIST = RoadLinkID,$(RoadLinkID),FromVal,$(FromVal),ToVal,$(ToVal)
    -> AttributeKeeper
AttributeKeeper
    KEEP_ATTRS = RoadLinkID,FromVal,ToVal
    -> Breakpoint_List [Events]

FME custom transformer node2geom

Parameters:
- VIAPUNKT = @Value(viapunkt)   # viapunkt
- nvdbApiAdr =

Input (input)
    -> AttributeCreator_URL
AttributeCreator_URL
    ATTR_TABLE = SET_TO href = $(nvdbApiAdr)vegnett/noder/$(VIAPUNKT)
    -> AttributeCreator
AttributeCreator
    ATTR_TABLE = SET_TO iter = 0
    -> Decelerator_2
loop_in (input)
    -> Decelerator_2
Decelerator_2
    DECEL_TYPE = Limit Features Per Second
    FEATURES_PER_SECOND = 10
    -> HTTPCaller_node2geom
HTTPCaller_node2geom
    CONNECTION_TIMEOUT_LENGTH = 60
    CUSTOM_HEADERS = Accept;application/vnd.vegvesen.nvdb-v3+xml X-Client;Elveg 2.0
    ERROR_ATTR = _error
    FOLLOW_REDIRECTS = Yes
    HTTP_METHOD = GET
    RESPONSE_HEADER_LIST_ATTR = _headers
    SAVE_FILE = Attribute
    STATUS_CODE_ATTR = _http_status_code
    TARGET_ATTR = _url_contents
    TARGET_ATTR_ENCODING = auto-detect
    TARGET_URL = @Value(href)
    TRANSFER_TIMEOUT_LENGTH = 90
    USE_COOKIES = No
    VERIFY_SSL_CERTIFICATES = Yes
    -> XMLFlattener
    <REJECTED> -> Tester
XMLFlattener
    ATTRIBUTE_XML = _url_contents
    EMBEDDED_EXPRESSIONS = node
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    XML_SOURCE_TYPE = Attribute with XML document
    -> AttributeExposer
AttributeExposer
    ATTR_LIST = geometri.wkt
    -> AttributeManager
AttributeManager
    ATTR_TABLE:
      REMOVE href
      REMOVE _headers{}.name
      REMOVE _headers{}.value
      REMOVE _url_contents
      REMOVE _http_status_code
      RENAME_SET_VALUE geometri.wkt > geom
    -> Output (output)
Output (output)
Tester
    BOOL_OP = OR
    TEST_CLAUSE = TEST @Value(iter) < 5
    PASSED -> AttributeManager_2
    FAILED -> Terminator
AttributeManager_2
    ATTR_TABLE = SET_TO iter = @int(@Value(iter))+1
    -> Decelerator
Decelerator
    DECEL_TYPE = Per Feature Delay
    DELAY = 15
    -> loop_in (output)
loop_in (output)
Terminator
    MESSAGE = Translation Terminated

FME custom transformer UniqeSegments

BREAKPOINTLIST (input)
    -> AttributeExposer_3
AttributeExposer_3
    ATTR_LIST = _idx,_maxIdx,RoadLinkID,_Bp_list{}.BREAKPOINT,_Bp_list{}.RoadLinkID,_Bp_list{}.fme_feature_type,_Bp_list{}.fme_basename,_Bp_list{}.fme_dataset
    -> ListIndexer

Bookmark: From value
ListIndexer
    INDEX = @Value(_idx)
    LIST_ATTR = _Bp_list{}
    -> AttributeExposer
AttributeExposer
    ATTR_LIST = BREAKPOINT
    -> AttributeManager
AttributeManager
    ATTR_TABLE:
      RENAME_SET_VALUE BREAKPOINT > FromVal
      SET_TO _next = @Evaluate(@Value(_idx)+1)
    -> ListIndexer_2

Bookmark: To value
ListIndexer_2
    INDEX = @Value(_next)
    LIST_ATTR = _Bp_list{}
    -> AttributeExposer_2
AttributeExposer_2
    ATTR_LIST = BREAKPOINT
    -> AttributeManager_2
AttributeManager_2
    ATTR_TABLE:
      RENAME_SET_VALUE BREAKPOINT > ToVal
      SET_TO _next = @Evaluate(@Value(_idx)+1)
    -> AttributeManager_3
    -> TestFilter

Bookmark: Finished segements
AttributeManager_3
    ATTR_TABLE:
      REMOVE _idx
      REMOVE _maxIdx
      REMOVE _next
      REMOVE _Bp_list{}.BREAKPOINT
      REMOVE _Bp_list{}.RoadLinkID
      REMOVE _Bp_list{}.fme_feature_type
      REMOVE _Bp_list{}.fme_basename
      REMOVE _Bp_list{}.fme_dataset
    -> Unique_Segments (output)
Unique_Segments (output)

Bookmark: Test for more segments
TestFilter
    DEFAULT_VALUE = <UNFILTERED>
    TEST_LIST = BOOL_OP,OR,COMPOSITE_TEST,<Unused>,TEST_CLAUSE,"TEST @Value(_next) = @Value(_maxIdx)",Last
    <UNFILTERED> -> AttributeCreator
AttributeCreator
    ATTR_TABLE = SET_TO _idx = @Value(_next)
    -> BREAKPOINTLIST (output)
BREAKPOINTLIST (output)

FME custom transformer Vegnett

Parameters:
- omr = kommune   # Områdetype
- gmlFolder = C:\wrk\SOSI-Vegnett\GML   # GML-hovedmappe
- xsdName = elveg20-hamar   # xsd Name
- OMR = @Value(omr)   # omr
- OMRNVN = @Value(omrNvn)   # omrNvn
- NESTE.HREF = @Value(neste.href)   # neste.href
- namespace = vegvesen.no.nvdb   # Namespace

_Input (input)
    -> AttributeCreator
AttributeCreator
    ATTR_TABLE = SET_TO iter = 0
    -> HTTPCaller_2
Loop (input)
    -> HTTPCaller_2
HTTPCaller_2
    CONNECTION_TIMEOUT_LENGTH = 60
    CUSTOM_HEADERS = Accept;application/vnd.vegvesen.nvdb-v3-rev1+xml X-Client;Elveg 2.0
    ERROR_ATTR = _error
    FOLLOW_REDIRECTS = Yes
    HTTP_METHOD = GET
    RESPONSE_HEADER_LIST_ATTR = _headers
    SAVE_FILE = Attribute
    STATUS_CODE_ATTR = _http_status_code
    TARGET_ATTR = _url_contents
    TARGET_ATTR_ENCODING = auto-detect
    TARGET_URL = @Value(neste.href)
    TRANSFER_TIMEOUT_LENGTH = 90
    USE_COOKIES = No
    VERIFY_SSL_CERTIFICATES = Yes
    -> XMLFragmenter_2
    -> XMLFragmenter
    <REJECTED> -> Tester
Note: Deler opp i en XML pr vegobjekt
XMLFragmenter
    ATTRIBUTE_XML = _url_contents
    EMBEDDED_EXPRESSIONS = objekter/veglenkesekvens
    FEATURE_TYPES_FORMAT_NAME = XML
    FLATTEN_OPTIONS:
      <structure
      separator="."
      open-list-brace="{"
      close-list-brace="}"
      map-empty-elements="yes"
      matched-prefix="attributes"
      matched-attributes="yes"
      matched-ancestor-attributes=""
      cardinality="+{?}"
      except=""
      structure-prefix=""
      child-position-attribute=""
      attribute-identifier=""/>

      <!--
      The options here allows customization of the attributes and attribute lists of the matched XML subtree
      that will be added to FME Features.

      Here are the following options that can be specified:

      1. separator
      This value of this option is used as the separator in the naming of the attributes of the children of the matched elements.

      Default value: .
      Possible values: any string

      2. open-list-brace
      Specifies the open list index delimiter brace for the flattened attributes.

      Default value: {
      Possible values: any string

      3. close-list-brace
      Specifies the close list index delimiter brace for the flattened attributes.

      Default value: }
      Possible values: any string

      4. map-empty-elements
      If set to yes, then any empty elements will be added as attributes with empty values onto the features.
      Otherwise, the attributes will not be added onto the features.

      Default value if not specified: yes
      Possible values: yes|no

      Default value:
      Possible values: any string

      5. matched-prefix
      This option controls whether FME feature attributes produced will be prefixed with matched element's name.
      If the value is 'yes', then both the matched element's attributes and all its children are prefixed
      If the value is 'no', then none of the feature attributes are prefixed with matched element's name
      If the value is 'children', then only the children of the matched element are prefixed
      If the value is 'attributes', then only the attributes of the matched element are prefixed

      Default value if not specified: yes
      Possible values: yes|no|children|attributes

      6. matched-attributes
      If this option is set to 'yes' then the attributes of the matched element are mapped as FME feature attributes.
      Otherwise, the attributes of the matched element are ignored.

      matched-prefix option can also be set to 'attributes' or 'yes' to allow the attributes to be prefixed with
      the name of the matched element.

      Default value if not specified: yes
      Possible values: yes|no

      7. matched-ancestor-attributes
      The option controls whether XML attributes from ancestor of the matched element should be included as FME feature attributes.

      The valid values for this option are:
      - 'parent' or '1'         : XML attributes of the parent of the matched element are added
      - 'grandparent' or '2'    : XML attributes of the grandparent of the matched element are added
      - 'root' or '-1'          : XML attributes of the root of the document are added
      - any non-negative number : XML attributes of the ancestor by going up x levels from the matched element are added.
                                  0 is the matched element.

      To include more than one ancestor, multiple values can be separated by a space.
      For example: To get the attributes from root, parent and grand parent, we can specify
      matched-ancestor-attributes="parent grandparent root"

      Default value:
      Possible values: parent|grandparent|root

      8. cardinality
      This option can be specified as a space separated list of cardinality directives.

      Default value: +{?} (Treat child elements as a list if there are more than one with the same name)
      Possible values: Refer to the documentation of XFMap section in XML Reader documentation

      9. structure-prefix
      This option can be set to non-empty string that serves as a prefix to every attribute that is generated for a matched element.

      Default value:
      Possible values: any string

      10. except
      The except attribute accepts the same types of expressions as the match or except attribute of a mapping rule.
      For example, the expression except=”parent/child{2}” could be used to exclude the second <child> element
      contained in a <parent> element from the output of the structure subrule.

      Default value:
      Possible values: any path expression

      11. child-position-attribute
      When this option is set to non-empty string, each child element will generate an additional feature attribute
      whose value will be the position of the child element witihin its parent.

      Default value:
      Possible values: any string

      12. attribute-identifier (Any string)
      XML attributes can be differentiated from leaf elements. By setting this option to non-empty string, XML reader
      will append a prefix to the attributes in the leaf elements.

      All the options have more elaborated examples and descriptions in the XML reader documentation.
      -->
    MERGE_ATTRS = No
    NEW_ATTRIBUTES = veglenkesekvensid
    REJECT_FEATURES_WITH_NO_FRAGMENTS = YES
    XML_SOURCE_TYPE = Attribute with XML document
    FRAGMENTS -> XMLFragmenter_3
Note: Deler opp i en XML pr vegobjekt
XMLFragmenter_3
    ATTRIBUTE_XML = xml_fragment
    EMBEDDED_EXPRESSIONS = veglenker/veglenke
    FEATURE_TYPES_FORMAT_NAME = XML
    FLATTEN_OPTIONS:
      <structure
      separator="."
      open-list-brace="{"
      close-list-brace="}"
      map-empty-elements="yes"
      matched-prefix="attributes"
      matched-attributes="yes"
      matched-ancestor-attributes=""
      cardinality="+{?}"
      except=""
      structure-prefix=""
      child-position-attribute=""
      attribute-identifier=""/>

      <!--
      The options here allows customization of the attributes and attribute lists of the matched XML subtree
      that will be added to FME Features.

      Here are the following options that can be specified:

      1. separator
      This value of this option is used as the separator in the naming of the attributes of the children of the matched elements.

      Default value: .
      Possible values: any string

      2. open-list-brace
      Specifies the open list index delimiter brace for the flattened attributes.

      Default value: {
      Possible values: any string

      3. close-list-brace
      Specifies the close list index delimiter brace for the flattened attributes.

      Default value: }
      Possible values: any string

      4. map-empty-elements
      If set to yes, then any empty elements will be added as attributes with empty values onto the features.
      Otherwise, the attributes will not be added onto the features.

      Default value if not specified: yes
      Possible values: yes|no

      Default value:
      Possible values: any string

      5. matched-prefix
      This option controls whether FME feature attributes produced will be prefixed with matched element's name.
      If the value is 'yes', then both the matched element's attributes and all its children are prefixed
      If the value is 'no', then none of the feature attributes are prefixed with matched element's name
      If the value is 'children', then only the children of the matched element are prefixed
      If the value is 'attributes', then only the attributes of the matched element are prefixed

      Default value if not specified: yes
      Possible values: yes|no|children|attributes

      6. matched-attributes
      If this option is set to 'yes' then the attributes of the matched element are mapped as FME feature attributes.
      Otherwise, the attributes of the matched element are ignored.

      matched-prefix option can also be set to 'attributes' or 'yes' to allow the attributes to be prefixed with
      the name of the matched element.

      Default value if not specified: yes
      Possible values: yes|no

      7. matched-ancestor-attributes
      The option controls whether XML attributes from ancestor of the matched element should be included as FME feature attributes.

      The valid values for this option are:
      - 'parent' or '1'         : XML attributes of the parent of the matched element are added
      - 'grandparent' or '2'    : XML attributes of the grandparent of the matched element are added
      - 'root' or '-1'          : XML attributes of the root of the document are added
      - any non-negative number : XML attributes of the ancestor by going up x levels from the matched element are added.
                                  0 is the matched element.

      To include more than one ancestor, multiple values can be separated by a space.
      For example: To get the attributes from root, parent and grand parent, we can specify
      matched-ancestor-attributes="parent grandparent root"

      Default value:
      Possible values: parent|grandparent|root

      8. cardinality
      This option can be specified as a space separated list of cardinality directives.

      Default value: +{?} (Treat child elements as a list if there are more than one with the same name)
      Possible values: Refer to the documentation of XFMap section in XML Reader documentation

      9. structure-prefix
      This option can be set to non-empty string that serves as a prefix to every attribute that is generated for a matched element.

      Default value:
      Possible values: any string

      10. except
      The except attribute accepts the same types of expressions as the match or except attribute of a mapping rule.
      For example, the expression except=”parent/child{2}” could be used to exclude the second <child> element
      contained in a <parent> element from the output of the structure subrule.

      Default value:
      Possible values: any path expression

      11. child-position-attribute
      When this option is set to non-empty string, each child element will generate an additional feature attribute
      whose value will be the position of the child element witihin its parent.

      Default value:
      Possible values: any string

      12. attribute-identifier (Any string)
      XML attributes can be differentiated from leaf elements. By setting this option to non-empty string, XML reader
      will append a prefix to the attributes in the leaf elements.

      All the options have more elaborated examples and descriptions in the XML reader documentation.
      -->
    MERGE_ATTRS = Yes
    REJECT_FEATURES_WITH_NO_FRAGMENTS = YES
    XML_SOURCE_TYPE = Attribute with XML document
    FRAGMENTS -> AttributeExposer
AttributeExposer
    ATTR_LIST = veglenkenummer,geometri.kvalitet.målemetode,geometri.kvalitet.nøyaktighet,geometri.kvalitet.nøyaktighetHøyde,geometri.kvalitet.maksimaltAvvik,geometri.kvalitet.synbarhet,veglenkesekvensid,geometri.kvalitet.målemetodeHøyde,geometri.medium,type,konnekteringslenke,geometri.datafangstdato
    -> AttributeRenamer
AttributeRenamer
    ATTR_TABLE = RENAME_SET_DEFAULT geometri.datafangstdato > datafangstdato
    -> DateFormatter
DateFormatter
    DATE_ATTR = datafangstdato
    FMT = ISO Date (%Y-%m-%d)
    INVALID_DATE_VALUE = 0001-01-01
    SRCFMT = Unknown - Automatic Detection
    -> AttributeValueMapper_3
AttributeValueMapper_3
    DEFAULT_VALUE = _FME_NO_OP_
    DIRECTION = Forward (Source To Destination)
    LUT = 10,terrengmåltUspesifisertMåleinstrument,11,terrengmåltTotalstasjon,12,terrengmåltTeodolittOgElAvstandsmåler,13,terrengmåltTeodolittOgMålebånd,14,terrengmåltOrtogonalmetoden,15,utmål,18,tattFraPlan,20,stereoinstrument,21,aerotriangulert,22,stereoinstrumentAnalytiskPlotter,23,stereoinstrumentAutograf,24,stereoinstrumentDigitalt,30,scannetFraKart,31,skannetFraKartBlyantoriginal,32,skannetFraKartRissefolie,33,skannetFraKartTransparentFolieGodKvalitet,34,skannetFraKartTransparentFolieMindreGodKvalitet,35,skannetFraKartPapirkopi,36,flybårenLaserscanner,37,bilbårenLaser,38,lineærReferanse,40,digitaliseringbordOrtofotoEllerFlybilde,41,digitaliseringbordOrtofotoFilm,42,digitaliseringbordOrtofotoFotokopi,43,digitaliseringbordFlybildeFilm,44,digitaliseringbordFlybildeFotokopi,45,digitalisertPåSkjermFraOrtofoto,46,digitalisertPåSkjermFraSatellittbilde,47,digitalisertPåSkjermFraAndreDigitaleRasterdata,48,digitalisertPåSkjermFraTolkningAvSeismikk,49,vektoriseringAvLaserdata,50,digitaliseringsbordKart,51,digitaliseringsbordKartBlyantoriginal,52,digitaliseringsbordKartRissefoile,53,digitaliseringsbordKartTransparentFoileGodKvalitet,54,digitaliseringsbordKartTransparentFoileMindreGodKvalitet,55,digitaliseringsbordKartPapirkopi,56,digitalisertPåSkjermFraSkannetKart,60,genererteDataInterpolasjon,61,genererteDataInterpolasjonTerrengmodell,62,genererteDataInterpolasjonVektetMiddel,63,genererteDataFraAnnenGeometri,64,genererteDataGeneralisering,65,genererteDataSentralpunkt,66,genererteDataSammenknytningspunktRandpunkt,67,koordinaterHentetFraGAB,68,koordinaterHentetFraJREG,69,beregnet,70,spesielleMetoder,71,spesielleMetoderMåltMedStikkstang,72,spesielleMetoderMåltMedWaterstang,73,spesielleMetoderMåltMedMålehjul,74,spesielleMetoderMåltMedStigningsmåler,77,fastsattPunkt,78,fastsattVedDomEllerKongeligResolusjon,80,frihåndstegning,81,frihåndstegningPåKart,82,frihåndstegningPåSkjerm,90,treghetsstedfesting,91,GNSSKodemålingRelativeMålinger,92,GNSSKodemålingEnkleMålinger,93,GNSSFasemålingStatiskMåling,94,GNSSFasemålingAndreMetoder,95,kombinasjonAvGNSSTreghet,96,GNSSFasemålingRTK,97,GNSSFasemålingFloat-løsning,99,ukjentMålemetode
    SRC = geometri.kvalitet.målemetode
    VAL_ATTR = kvalitet.Posisjonskvalitet.målemetode
    -> AttributeValueMapper_4
AttributeValueMapper_4
    DEFAULT_VALUE = _FME_NO_OP_
    DIRECTION = Forward (Source To Destination)
    LUT = 0,fulltSynligOgGjenfinnbarITerrenget,1,dårligGjenfinnbarITerreng,2,middelsSynligIFlybilde,3,dårligSynligIFlybilde
    SRC = geometri.kvalitet.synbarhet
    VAL_ATTR = kvalitet.Posisjonskvalitet.synbarhet
    -> AttributeValueMapper_5
AttributeValueMapper_5
    DEFAULT_VALUE = _FME_NO_OP_
    DIRECTION = Forward (Source To Destination)
    LUT = 10,terrengmåltUspesifisertMåleinstrument,11,terrengmåltTotalstasjon,12,terrengmåltTeodolittOgElAvstandsmåler,13,terrengmåltTeodolittOgMålebånd,14,terrengmåltOrtogonalmetoden,15,nivellement,18,tattFraPlan,20,stereoinstrument,21,aerotriangulert,22,stereoinstrumentAnalytiskPlotter,23,stereoinstrumentAutograf,24,stereoinstrumentDigitalt,36,flybårenLaserscanning,60,genererteDataInterpolasjon,61,genererteDataInterpolasjonTerrengmodell,62,genererteDataInterpolasjonVektetMiddel,63,genererteDataFraAnnenGeometri,64,genererteDataGeneralisering,66,genererteDataSammenknytningspunktRandpunkt,67,koordinaterHentetFraGAB,68,koordinaterHentetFraJREG,69,beregnet,70,spesielleMetoder,74,spesielleMetoderMåltMedStigningsmåler,78,fastsattVedDomEllerKongeligResolusjon,79,annetSpesifiseresIFilhode,90,treghetsstedfesting,91,GNSSKodemålingRelativeMålinger,92,GNSSKodemålingEnkleMålinger,93,GNSSFasemålingStatiskMåling,94,GNSSFasemålingAndreMetoder,95,kombinasjonAvGNSSTreghet,96,GNSSFasemålingRTK,99,ukjentMålemetode
    SRC = geometri.kvalitet.målemetodeHøyde
    VAL_ATTR = kvalitet.Posisjonskvalitet.målemetodeHøyde
    -> AttributeManager_8
AttributeManager_8
    ATTR_TABLE:
      SET_TO kvalitet.Posisjonskvalitet.målemetodeHøyde
      SET_TO konnekteringslenke = FME_CONDITIONAL:DEFAULT_VALUE'false'BOOL_OP;OR;COMPOSITE_TEST;<Unused>;TEST @Value(type) = KONNEKTERING'true'FME_NUM_CONDITIONS2___
      SET_TO kvalitet.Posisjonskvalitet.nøyaktighet = FME_CONDITIONAL:DEFAULT_VALUE'_FME_NO_OP_'BOOL_OP;OR;COMPOSITE_TEST;<Unused>;TEST @Value(geometri.kvalitet.nøyaktighet) != -1'@Value(geometri.kvalitet.nøyaktighet)'FME_NUM_CONDITIONS2___
      SET_TO kvalitet.Posisjonskvalitet.nøyaktighetHøyde = FME_CONDITIONAL:DEFAULT_VALUE'_FME_NO_OP_'BOOL_OP;OR;COMPOSITE_TEST;<Unused>;TEST @Value(geometri.kvalitet.nøyaktighetHøyde) != -1'@Value(geometri.kvalitet.nøyaktighetHøyde)'FME_NUM_CONDITIONS2___
      SET_TO kvalitet.Posisjonskvalitet.maksimaltAvvik = FME_CONDITIONAL:DEFAULT_VALUE'_FME_NO_OP_'BOOL_OP;OR;COMPOSITE_TEST;<Unused>;TEST @Value(geometri.kvalitet.maksimaltAvvik) != -1'@Value(geometri.kvalitet.maksimaltAvvik)'FME_NUM_CONDITIONS2___
      SET_TO medium = FME_CONDITIONAL:DEFAULT_VALUE'_FME_NO_OP_'BOOL_OP;OR;COMPOSITE_TEST;<Unused>;TEST geometri.medium ATTRIBUTE_HAS_A_VALUE _FME_BLANK_STRING_'@Value(geometri.medium)'FME_NUM_CONDITIONS2___
    -> PythonCaller
PythonCaller
    PYTHONSOURCE:
      import fme
      import fmeobjects

      def processFeature(feature):
          medium = feature.getAttribute('geometri.medium{0}')
          if medium:
              feature.removeAttribute('geometri.medium{}')
              feature.setAttribute('geometri.medium', medium)
    PYTHONSYMBOL = processFeature
    -> AttributeValueMapper_6
AttributeValueMapper_6
    DIRECTION = Forward (Source To Destination)
    LUT = B,iBygning,D,tidvisUnderVann,I,påIsbre,J,underIsbre,L,iLuft,O,påVannoverflaten,S,påSjøbunnen,T,påTerrenget,U,underTerrenget,V,alltidIVann,W,underSjøbunnen,X,ukjent
    SRC = geometri.medium
    VAL_ATTR = medium
    -> NullAttributeMapper
NullAttributeMapper
    ATTRCHOICE = Selected Attributes
    ATTRLIST = kvalitet.Posisjonskvalitet.målemetodeHøyde kvalitet.Posisjonskvalitet.maksimaltAvvik medium kvalitet.Posisjonskvalitet.nøyaktighetHøyde kvalitet.Posisjonskvalitet.nøyaktighet kvalitet.Posisjonskvalitet.målemetode kvalitet.Posisjonskvalitet.synbarhet
    NULL_TREATMENT = Missing
    REG_EXP = ^$
    SOURCE_ATTR_VAL = Null
    -> Veglenke (output)
Veglenke (output)
Tester
    BOOL_OP = OR
    TEST_CLAUSE = TEST @Value(iter) < 5
    PASSED -> AttributeManager_2
    FAILED -> Terminator
Terminator
    MESSAGE = Translation Terminated
AttributeManager_2
    ATTR_TABLE = SET_TO iter = @int(@Value(iter))+1
    -> Decelerator
Decelerator
    DECEL_TYPE = Per Feature Delay
    DELAY = 15
    -> Loop (output)
XMLFragmenter_2
    ATTRIBUTE_XML = _url_contents
    EMBEDDED_EXPRESSIONS = side/metadata
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = No
    NEW_ATTRIBUTES = returnert neste.href
    REJECT_FEATURES_WITH_NO_FRAGMENTS = YES
    XML_SOURCE_TYPE = Attribute with XML document
    FRAGMENTS -> TestFilter
TestFilter
    DEFAULT_VALUE = <UNFILTERED>
    TEST_LIST = BOOL_OP,OR,COMPOSITE_TEST,<Unused>,TEST_CLAUSE,"TEST @Value(returnert) != 0",Flere
    Flere -> Loop (output)
Loop (output)

FME custom transformer BreakpointList

Parameters:
- FROMVAL = @Value(FromVal)   # Fromval
- TOVAL = @Value(ToVal)   # Toval
- ROADLINKID = @Value(RoadLinkID)   # Roadlinkid

Events (input)
    -> ATTRIBUTERENAMER_4
    -> ATTRIBUTERENAMER_3
Breakpoint_List (output)

Bookmark: Create a list of all unique breakpoints pr RoadLinkID
Note: From
ATTRIBUTERENAMER_3: AttributeRenamer
    ATTR_LIST = BREAKPOINT,FromVal
    -> AttributeKeeper
Note: To
ATTRIBUTERENAMER_4: AttributeRenamer
    ATTR_LIST = BREAKPOINT,ToVal
    -> AttributeKeeper
AttributeKeeper
    KEEP_ATTRS = RoadLinkID,BREAKPOINT
    -> ListBuilder
ListBuilder
    GRP_BY = RoadLinkID
    LIST_NAME = _Bp_list
    -> ListDuplicateRemover
ListDuplicateRemover
    SRC_LIST = _Bp_list{}.BREAKPOINT
    -> ListSorter
ListSorter
    ORDER = Increasing
    SRC_LIST = _Bp_list{}.BREAKPOINT
    TYPE = Numeric
    -> Breakpoint_List (output)

FME custom transformer UniqeSegments_2

Parameters:
- LIST_ATTR = _Bp_list{}   # " " "" Bp List{}
- _IDX = @Value(_idx)   # Idx
- ROADLINKID = @Value(RoadLinkID)   # Roadlinkid
- _ELEMENT_COUNT = @Value(_element_count)   # Element Count
- _MAXIDX = @Value(_maxIdx)   # Maxidx

BREAKPOINTLIST (input)
    -> ListIndexer
ListIndexer
    INDEX = @Value(_idx)
    LIST_ATTR = $(LIST_ATTR)
    -> AttributeExposer
AttributeExposer
    ATTR_LIST = BREAKPOINT
    -> AttributeRenamer
AttributeRenamer
    ATTR_LIST = FromVal,BREAKPOINT
    -> ExpressionEvaluator
ExpressionEvaluator
    EXPRESSION = @Value(_idx)+1
    VAL_ATTR = _next
    -> ListIndexer_2
ListIndexer_2
    INDEX = @Value(_next)
    LIST_ATTR = $(LIST_ATTR)
    -> AttributeExposer_2
AttributeExposer_2
    ATTR_LIST = BREAKPOINT
    -> AttributeRenamer_2
AttributeRenamer_2
    ATTR_LIST = ToVal,BREAKPOINT
    -> ListRemover
    -> Tester
ListRemover
    LIST_ATTR = $(LIST_ATTR)
    -> AttributeKeeper
AttributeKeeper
    KEEP_ATTRS = FromVal,RoadLinkID,ToVal
    -> Unique_Segments (output)
Unique_Segments (output)
Tester
    BOOL_OP = OR
    TEST_CLAUSE = TEST "@Value(_next)" < "@Value(_maxIdx)"
    PASSED -> AttributeSetter
AttributeSetter
    DEST_ATTR = _idx
    VAL = @Value(_next)
    -> BREAKPOINTLIST (output)
BREAKPOINTLIST (output)

FME custom transformer SegmentizeTable_2
Splits an event table based on a list of segments with from-to-measure

Parameters:
- eventRoadLink = HPid   # Event Table Road Link ID Attribute
- eventFromVal = fra_meter   # Event Table from meassure
- eventToVal = til_meter   # Event Table To Meassure

Events (input)
    -> AttributeCreator
SegmentList (input)
    -> AttributeExposer
Note: Create common segments
InlineQuerier
    QUERY_DEF:
      EventSegments,Select * FROM Events
      INNER JOIN Segments ON Events.RoadLinkID = Segments.RoadLinkID
      WHERE (Segments.segFromVal < Events.eventToVal AND Segments.segToVal > Events.eventFromVal),FIRST
    QUERY_SCHEMA = EventSegments,RoadLinkID,varchar(30),eventFromVal,float,eventToVal,float,Events.fme_feature_content,fme_feature_content,segFromVal,float,segToVal,float,Segments.fme_feature_content,fme_feature_content
    TABLE_DEF = Events,RoadLinkID,varchar(30),eventFromVal,float,eventToVal,float,Segments,RoadLinkID,varchar(30),segFromVal,float,segToVal,float
    EventSegments -> ATTRIBUTEREMOVER_2
ATTRIBUTEREMOVER_2: AttributeRemover
    REMOVE_ATTRS = eventFromVal,eventToVal
    -> AttributeRenamer
AttributeRenamer
    ATTR_LIST = FromVal,segFromVal,ToVal,segToVal
    -> Segmented (output)
Segmented (output)

Bookmark: Link ID and measure attributes
AttributeCreator
    ATTR_LIST = RoadLinkID,$(eventRoadLink),eventFromVal,$(eventFromVal),eventToVal,$(eventToVal)
    -> InlineQuerier [Events]
AttributeExposer
    ATTR_LIST = RoadLinkID,FromVal,ToVal
    -> AttributeExpressionRenamer
AttributeExpressionRenamer
    ATTRCHOICE = Selected Attributes
    ATTRLIST = FromVal ToVal
    PATTERN_ACTION_DISP = Add String Prefix
    REPLACE_STR = seg
    -> InlineQuerier [Segments]

FME custom transformer Vegobjekter
Leser og tolker data fra NVDB-API

Parameters:
- NESTE.HREF = @Value(neste.href)   # neste.href

_Input (input)
    -> AttributeCreator
AttributeCreator
    ATTR_TABLE = SET_TO iter = 0
    -> HTTPCaller_2
Loop (input)
    -> HTTPCaller_2
HTTPCaller_2
    CONNECTION_TIMEOUT_LENGTH = 60
    CUSTOM_HEADERS = Accept;application/vnd.vegvesen.nvdb-v3-rev1+xml X-Client;Elveg 2.0
    ERROR_ATTR = _error
    FOLLOW_REDIRECTS = Yes
    HTTP_METHOD = GET
    RESPONSE_HEADER_LIST_ATTR = _headers
    SAVE_FILE = Attribute
    STATUS_CODE_ATTR = _http_status_code
    TARGET_ATTR = _url_contents
    TARGET_ATTR_ENCODING = auto-detect
    TARGET_URL = @Value(neste.href)
    TRANSFER_TIMEOUT_LENGTH = 90
    USE_COOKIES = No
    VERIFY_SSL_CERTIFICATES = Yes
    -> XMLFragmenter_2
    -> XMLFragmenter
    <REJECTED> -> Tester
Note: Deler opp i en XML pr vegobjekt
XMLFragmenter
    ATTRIBUTE_XML = _url_contents
    EMBEDDED_EXPRESSIONS = vegobjekt
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = No
    NEW_ATTRIBUTES = id geometri.wkt metadata.versjon metadata.type.id egenskaper.egenskap{}.id egenskaper.egenskap{}.enum_id egenskaper.egenskap{}.verdi geometri.egengeometri geometri.srid lokasjon.stedfestinger.stedfesting{}.veglenkesekvens lokasjon.stedfestinger.stedfesting{}.startposisjon lokasjon.stedfestinger.stedfesting{}.sluttposisjon lokasjon.stedfestinger.stedfesting{}
    XML_SOURCE_TYPE = Attribute with XML document
    FRAGMENTS -> PythonCaller_objekt_featureIdVersion
Output (output)
Tester
    BOOL_OP = OR
    TEST_CLAUSE = TEST @Value(iter) < 5
    PASSED -> AttributeManager_2
    FAILED -> Terminator
Terminator
    MESSAGE = Translation Terminated
AttributeManager_2
    ATTR_TABLE = SET_TO iter = @int(@Value(iter))+1
    -> Decelerator
Decelerator
    DECEL_TYPE = Per Feature Delay
    DELAY = 15
    -> Loop (output)
XMLFragmenter_2
    ATTRIBUTE_XML = _url_contents
    EMBEDDED_EXPRESSIONS = side/metadata
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = No
    NEW_ATTRIBUTES = returnert neste.href
    XML_SOURCE_TYPE = Attribute with XML document
    FRAGMENTS -> TestFilter
TestFilter
    DEFAULT_VALUE = <UNFILTERED>
    TEST_LIST = BOOL_OP,OR,COMPOSITE_TEST,<Unused>,TEST_CLAUSE,"TEST @Value(returnert) != 0",Flere
    Flere -> Loop (output)
Loop (output)

Bookmark: Oversetter fra NVDB-API-XML
PythonCaller_objekt_featureIdVersion
    NEW_ATTRIBUTES = geometri fme_feature_type identifikasjon.Identifikasjon.lokalId identifikasjon.Identifikasjon.versjonId identifikasjon.Identifikasjon.navnerom gml_id assosiasjoner{}.typeId assosiasjoner{}.vegobjektId assosiasjoner{}.relasjonstype
    PYTHONSOURCE:
      import fme
      import fmeobjects

      ns='vegvesen.no.nvdb' # FME_MacroValues['namespace']

      def featureIdVersion(feature):
          # Setter feature type
          ft=str(feature.getAttribute('metadata.type.id'))
          feature.setAttribute('fme_feature_type',ft)
          feature.removeAttribute('metadata.type.id')
          # ID og versjon
          feature.setAttribute('identifikasjon.Identifikasjon.navnerom', ns)
          v=feature.getAttribute('id')
          feature.setAttribute('NVDB_ID', v)
          feature.setAttribute('identifikasjon.Identifikasjon.lokalId', v)
          feature.setAttribute('gml_id', ns + '.' + v)
          feature.removeAttribute('id')
          v=feature.getAttribute('metadata.versjon')
          feature.setAttribute('versjonsID', v)
          feature.setAttribute('identifikasjon.Identifikasjon.versjonId', v)
          feature.removeAttribute('metadata.versjon')

          # Kommune
          #v=feature.getAttribute('lokasjon.kommuner.kommune')
          #feature.setAttribute('kommunenummer', v.zfill(4))
          #feature.removeAttribute('lokasjon.kommuner.kommune')
    PYTHONSYMBOL = featureIdVersion
    -> PythonCaller_objekt_egenskaper
PythonCaller_objekt_egenskaper
    NEW_ATTRIBUTES = geometri fme_feature_type identifikasjon.Identifikasjon.lokalId identifikasjon.Identifikasjon.versjonId identifikasjon.Identifikasjon.navnerom gml_id assosiasjoner{}.typeId assosiasjoner{}.vegobjektId assosiasjoner{}.relasjonstype epsg lineærPosisjon{}.LineærPosisjonStrekning.lenkesekvens.Identifikasjon.lokalId lineærPosisjon{}.LineærPosisjonStrekning.lenkesekvens.Identifikasjon.navnerom lineærPosisjon{}.LineærPosisjonStrekning.startposisjon lineærPosisjon{}.LineærPosisjonStrekning.sluttposisjon kommunenummer
    PYTHONSOURCE:
      import fme
      import fmeobjects

      def egenskaper(feature):
          i = 0
          while True:
              n = feature.getAttribute('egenskaper.egenskap{%d}.id' % i)
              e = str(feature.getAttribute('egenskaper.egenskap{%d}.enum_id' % i))
              nId = feature.getAttribute('egenskaper.egenskap{%d}.innhold.egenskap.netelementid' % i)
              if nId != None:
                  feature.setAttribute('netelementid', str(nId))
              fraPos = feature.getAttribute('egenskaper.egenskap{%d}.innhold.egenskap.fra_posisjon' % i)
              if fraPos != None:
                  feature.setAttribute('fraPos', float(fraPos))
              tilPos = feature.getAttribute('egenskaper.egenskap{%d}.innhold.egenskap.til_posisjon' % i)
              if tilPos != None:
                  feature.setAttribute('tilPos', float(tilPos))
              v = feature.getAttribute('egenskaper.egenskap{%d}.verdi' % i)
              if v == None:
                  if i>0:
                      break
                  else:
                      # Kun én egenskap, ikke liste
                      n = feature.getAttribute('egenskaper.egenskap.id')
                      e = str(feature.getAttribute('egenskaper.egenskap.enum_id'))
                      v = feature.getAttribute('egenskaper.egenskap.verdi')


              if n != None:
                  if e == 'None':
                      # if (n == 'Kommunenummer' and v == 0):
                      feature.setAttribute(n, v)
                  else:
                      # Enumverdi for kodelisteverdier
                      feature.setAttribute(n, e)

              i += 1
    PYTHONSYMBOL = egenskaper
    -> PythonCaller_objekt_geometri
PythonCaller_objekt_geometri
    NEW_ATTRIBUTES = geometri fme_feature_type identifikasjon.Identifikasjon.lokalId identifikasjon.Identifikasjon.versjonId identifikasjon.Identifikasjon.navnerom gml_id assosiasjoner{}.typeId assosiasjoner{}.vegobjektId assosiasjoner{}.relasjonstype epsg lineærPosisjon{}.LineærPosisjonStrekning.lenkesekvens.Identifikasjon.lokalId lineærPosisjon{}.LineærPosisjonStrekning.lenkesekvens.Identifikasjon.navnerom lineærPosisjon{}.LineærPosisjonStrekning.startposisjon lineærPosisjon{}.LineærPosisjonStrekning.sluttposisjon kommunenummer
    PYTHONSOURCE:
      import fme
      import fmeobjects

      ns='vegvesen.no.nvdb' # FME_MacroValues['namespace']

      def geometri(feature):
          v=feature.getAttribute('geometri.wkt')
          if v != None:
              feature.setAttribute('geometri', v)
          feature.removeAttribute('geometri.wkt')
          v=feature.getAttribute('geometri.egengeometri')
          if v != None:
              feature.setAttribute('egengeometri', v)
          if v == 'true':
              feature.setAttribute('prosesshistorie', 'Geometri: Egengeometri fra NVDB')
          else:
              feature.setAttribute('prosesshistorie', 'Geometri: Generert fra lineære referanser til vegnett i NVDB')
          feature.removeAttribute('geometri.egengeometri')
          v=feature.getAttribute('geometri.srid')
          if v != None:
              feature.setAttribute('epsg', 'EPSG:'+v)
          feature.removeAttribute('geometri.srid')
    PYTHONSYMBOL = geometri
    -> PythonCaller_objekt_stedfestingBasisnett
PythonCaller_objekt_stedfestingBasisnett
    NEW_ATTRIBUTES = geometri fme_feature_type identifikasjon.Identifikasjon.lokalId identifikasjon.Identifikasjon.versjonId identifikasjon.Identifikasjon.navnerom gml_id assosiasjoner{}.typeId assosiasjoner{}.vegobjektId assosiasjoner{}.relasjonstype epsg lineærPosisjon{}.LineærPosisjonStrekning.lenkesekvens.Identifikasjon.lokalId lineærPosisjon{}.LineærPosisjonStrekning.lenkesekvens.Identifikasjon.navnerom lineærPosisjon{}.LineærPosisjonStrekning.startposisjon lineærPosisjon{}.LineærPosisjonStrekning.sluttposisjon kommunenummer
    PYTHONSOURCE:
      import fme
      import fmeobjects

      ns='vegvesen.no.nvdb' # FME_MacroValues['namespace']

      def stedfestingBasisnett(feature):
       # Stedfesting i basisnettet
          i = 0
          while True:
              v = str(feature.getAttribute('lokasjon.stedfestinger.stedfesting{%d}.veglenkesekvensid' % i))
              if v == 'None':
                  if i>0:
                      break
                  else:
                      # Kun en stedfesting, hent fra attributt i stedet for fra liste
                      v = str(feature.getAttribute('lokasjon.stedfestinger.stedfesting.relativPosisjon'))
                      if v == 'None':
                          #Ikke verdi for "posisjon", dvs strekningsstedfesting (eller ingen!)
                          v = str(feature.getAttribute('lokasjon.stedfestinger.stedfesting.veglenkesekvensid'))
                          if v != 'None':
                              feature.setAttribute('veglenkesekvens', v)
                              #feature.setAttribute(u'lineærPosisjon{%d}.LineærPosisjonStrekning.nettverkselement.xlink_href' % i, 'Veglenke.gml#' + ns + '.rl.' + v)
                              #feature.setAttribute(u'lineærPosisjon{%d}.LineærPosisjonStrekning.veglenkesekvens' % i, v)
                              feature.setAttribute(u'lineærPosisjon{%d}.LineærPosisjonStrekning.lenkesekvens.Identifikasjon.navnerom' % i, ns + '.rls')
                              feature.setAttribute(u'lineærPosisjon{%d}.LineærPosisjonStrekning.lenkesekvens.Identifikasjon.lokalId' % i, v)
                          v = str(feature.getAttribute('lokasjon.stedfestinger.stedfesting.startposisjon'))
                          if v != 'None':
                              feature.setAttribute(u'lineærPosisjon{%d}.LineærPosisjonStrekning.fraPosisjon' % i, v)
                          v = str(feature.getAttribute('lokasjon.stedfestinger.stedfesting.sluttposisjon'))
                          if v != 'None':
                              feature.setAttribute(u'lineærPosisjon{%d}.LineærPosisjonStrekning.tilPosisjon' % i, v)

                          v = str(feature.getAttribute('lokasjon.stedfestinger.stedfesting.sideposisjon'))
                          if v != 'None':
                              feature.setAttribute(u'lineærPosisjon{%d}.LineærPosisjonStrekning.sideposisjon' % i, v)

                          v = feature.getAttribute('lokasjon.stedfestinger.stedfesting.kjørefelt.felt{}')
                          if not v: v = feature.getAttribute('lokasjon.stedfestinger.stedfesting.kjørefelt.felt')
                          if v != 'None':
                              feature.setAttribute(u'lineærPosisjon{%d}.LineærPosisjonStrekning.felt' % i, v)

                          v = str(feature.getAttribute('lokasjon.stedfestinger.stedfesting.retning'))
                          if v != 'None':
                              feature.setAttribute('retning', v)
                              feature.setAttribute(u'lineærPosisjon{%d}.LineærPosisjonStrekning.retning' % i, v.lower())
                          feature.setAttribute(u'lineærPosisjon{%d}.LineærPosisjonStrekning.lineærReferanseMetode' % i, 'normalisert')

                      else:
                          # Punktstedfesting
                          v = str(feature.getAttribute('lokasjon.stedfestinger.stedfesting.veglenkesekvensid'))
                          if v != 'None':
                              feature.setAttribute('veglenkesekvens', v)
                              #feature.setAttribute(u'lineærPosisjon{%d}.LineærPosisjonPunkt.nettverkselement.xlink_href' % i, 'Veglenke.gml#' + ns + '.rl.' + v)
                              #feature.setAttribute(u'lineærPosisjon{%d}.LineærPosisjonPunkt.veglenkesekvens' % i, v)
                          feature.setAttribute(u'lineærPosisjon{%d}.LineærPosisjonPunkt.lenkesekvens.Identifikasjon.navnerom'  % i, ns + '.rls')
                          feature.setAttribute(u'lineærPosisjon{%d}.LineærPosisjonPunkt.lenkesekvens.Identifikasjon.lokalId'  % i, v)

                          v = str(feature.getAttribute('lokasjon.stedfestinger.stedfesting.relativPosisjon'))
                          if v != 'None':
                              feature.setAttribute(u'lineærPosisjon{%d}.LineærPosisjonPunkt.posisjon' % i, v)

                          v = str(feature.getAttribute(u'lokasjon.stedfestinger.stedfesting.sideposisjon'))
                          if v != 'None':
                              feature.setAttribute(u'lineærPosisjon{%d}.LineærPosisjonPunkt.sideposisjon' % i, v)
                          feature.setAttribute(u'lineærPosisjon{%d}.LineærPosisjonPunkt.lineærReferanseMetode' % i, 'normalisert')

                      feature.removeAttribute('lokasjon.stedfestinger.stedfesting.veglenkesekvensid')
                      feature.removeAttribute('lokasjon.stedfestinger.stedfesting.startposisjon')
                      feature.removeAttribute('lokasjon.stedfestinger.stedfesting.sluttposisjon')
                      feature.removeAttribute('lokasjon.stedfestinger.stedfesting.posisjon')
                      feature.removeAttribute('lokasjon.stedfestinger.stedfesting.sideposisjon')
                      feature.removeAttribute('lokasjon.stedfestinger.stedfesting.retning')
                      feature.removeAttribute('lokasjon.stedfestinger.stedfesting.kortform')
              else:
                  # Bygg LineærPosisjon-liste fra stedfestingsliste
                  v = str(feature.getAttribute('lokasjon.stedfestinger.stedfesting{%d}.posisjon' % i))
                  if v == 'None':
                      #Ikke verdi for "posisjon", dvs strekningsstedfesting
                      v = str(feature.getAttribute('lokasjon.stedfestinger.stedfesting{%d}.veglenkesekvensid' % i))
                      if v != 'None':
                          feature.setAttribute('veglenkesekvens', v)
                          #feature.setAttribute(u'lineærPosisjon{%d}.LineærPosisjonStrekning.nettverkselement.xlink_href' % i, 'Veglenke.gml#' + ns + '.rl.' + v)
                          #feature.setAttribute(u'lineærPosisjon{%d}.LineærPosisjonStrekning.veglenkesekvens' % i, v)
                          feature.setAttribute(u'lineærPosisjon{%d}.LineærPosisjonStrekning.lenkesekvens.Identifikasjon.navnerom'  % i, ns + '.rls')
                          feature.setAttribute(u'lineærPosisjon{%d}.LineærPosisjonStrekning.lenkesekvens.Identifikasjon.lokalId'  % i, v)

                      v = str(feature.getAttribute('lokasjon.stedfestinger.stedfesting{%d}.startposisjon' % i))
                      if v != 'None':
                          feature.setAttribute(u'lineærPosisjon{%d}.LineærPosisjonStrekning.fraPosisjon' % i, v)

                      v = str(feature.getAttribute('lokasjon.stedfestinger.stedfesting{%d}.sluttposisjon' % i))
                      if v != 'None':
                          feature.setAttribute(u'lineærPosisjon{%d}.LineærPosisjonStrekning.tilPosisjon' % i, v)

                      v = str(feature.getAttribute('lokasjon.stedfestinger.stedfesting{%d}.sideposisjon' % i))
                      if v != 'None':
                          feature.setAttribute(u'lineærPosisjon{%d}.LineærPosisjonStrekning.sideposisjon' % i, v)


                      v = feature.getAttribute('lokasjon.stedfestinger.stedfesting{%d}.kjørefelt.felt{}' % i)
                      if not v: v = feature.getAttribute('lokasjon.stedfestinger.stedfesting{%d}.kjørefelt.felt' % i)
                      if v != 'None':
                          feature.setAttribute(u'lineærPosisjon{%d}.LineærPosisjonStrekning.felt' % i, v)

                      v = str(feature.getAttribute('lokasjon.stedfestinger.stedfesting{%d}.retning' % i))
                      if v != 'None':
                          feature.setAttribute('retning', v)
                          feature.setAttribute(u'lineærPosisjon{%d}.LineærPosisjonStrekning.retning' % i, v.lower())
                      feature.setAttribute(u'lineærPosisjon{%d}.LineærPosisjonStrekning.lineærReferanseMetode' % i, 'normalisert')

                  else:
                      # Punktstedfesting
                      v = str(feature.getAttribute('lokasjon.stedfestinger.stedfesting{%d}.veglenkesekvensid' % i))
                      if v != 'None':
                          feature.setAttribute('veglenkesekvens', v)
                          #feature.setAttribute(u'lineærPosisjon{%d}.LineærPosisjonPunkt.nettverkselement.xlink_href' % i, 'Veglenke.gml#' + ns + '.rl.' + v)
                          #feature.setAttribute(u'lineærPosisjon{%d}.LineærPosisjonPunkt.veglenkesekvens' % i, v)
                          feature.setAttribute(u'lineærPosisjon{%d}.LineærPosisjonPunkt.lenkesekvens.Identifikasjon.navnerom'  % i, ns + '.rls')
                          feature.setAttribute(u'lineærPosisjon{%d}.LineærPosisjonPunkt.lenkesekvens.Identifikasjon.lokalId'  % i, v)

                      v = str(feature.getAttribute('lokasjon.stedfestinger.stedfesting{%d}.posisjon' % i))
                      if v != 'None':
                          feature.setAttribute(u'lineærPosisjon{%d}.LineærPosisjonPunkt.posisjon' % i, v)

                      v = str(feature.getAttribute('lokasjon.stedfestinger.stedfesting{%d}.sideposisjon' % i))
                      if v != 'None':
                          feature.setAttribute(u'lineærPosisjon{%d}.LineærPosisjonPunkt.sideposisjon' % i, v)
                      feature.setAttribute(u'lineærPosisjon{%d}.LineærPosisjonPunkt.lineærReferanseMetode' % i, 'normalisert')

                  feature.removeAttribute('lokasjon.stedfestinger.stedfesting{%d}.veglenkesekvensid' % i)
                  feature.removeAttribute('lokasjon.stedfestinger.stedfesting{%d}.startposisjon' % i)
                  feature.removeAttribute('lokasjon.stedfestinger.stedfesting{%d}.sluttposisjon' % i)
                  feature.removeAttribute('lokasjon.stedfestinger.stedfesting{%d}.posisjon' % i)
                  feature.removeAttribute('lokasjon.stedfestinger.stedfesting{%d}.sideposisjon' % i)
                  feature.removeAttribute('lokasjon.stedfestinger.stedfesting{%d}.retning' % i)
                  feature.removeAttribute('lokasjon.stedfestinger.stedfesting{%d}.kortform' % i)
              i += 1
    PYTHONSYMBOL = stedfestingBasisnett
    -> AttributeExposer
AttributeExposer
    ATTR_LIST = metadata.sist_modifisert
    -> AttributeManager
AttributeManager
    ATTR_TABLE = RENAME_SET_VALUE metadata.sist_modifisert > oppdateringsdato
    -> Output (output)
