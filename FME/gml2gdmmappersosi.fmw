FME workspace gml2gdmmappersosi.fmw
Startup Python:
      import fme
      import fmeobjects
      from linrefTools import *

Parameters:
- kommune = 5418   # Kommune
- mainFolder = C:\DATA\GIT\SOSI-Vegnett   # Hovedmappe

Readers:
- GML_1: GML from $(mainFolder)\GML\kommune\$(kommune)\*.gml

Writers:
- GDMMAPPERSOSI_1: GDMMAPPERSOSI to $(kommune) in EPSG:25833

Note: Pakker ut liste for lineærPosisjon
ListExploder
    ATTR_ACCUM_MODE = Merge Incoming List
    ATTR_CONFLICT_RES = Use Incoming List
    INDEX_ATTR = _element_index
    LIST_ATTR = lineærPosisjon{}
    ELEMENTS -> BulkAttributeRenamer_2
    <REJECTED> -> BulkAttributeRenamer_2
Note: Fjerner eventuelt gjenværende lineærPosisjon-prefikser
BulkAttributeRenamer_2
    ATTRCHOICE = All Attributes
    CASE_DISP = YES
    MODE_CHOICE = RENAME
    PATTERN_ACTION_DISP = REMOVEPREFIX
    REPLACE_STR = lineærPosisjon.
    -> AttributeExposer
AttributeExposer
    ATTR_LIST = fme_feature_type
    -> BulkAttributeRenamer
Note: Setter alle attributtnavn til store bokstaver
BulkAttributeRenamer
    ATTRCHOICE = All Attributes
    CASE_CHANGE_TYPE = upper
    MODE_CHOICE = RENAME
    PATTERN_ACTION_DISP = CASECHANGE
    -> AttributeManager
Note: Individuelle endringer for en del attributter
AttributeManager
    ATTR_TABLE:
      REMOVE GML_PARENT_ID
      REMOVE GML_PARENT_PROPERTY
      REMOVE GML_ID
      RENAME_SET_VALUE IDENTIFIKASJON.IDENTIFIKASJON.LOKALID > IDENT.LOKALID
      RENAME_SET_VALUE IDENTIFIKASJON.IDENTIFIKASJON.NAVNEROM > IDENT.NAVNEROM
      RENAME_SET_VALUE IDENTIFIKASJON.IDENTIFIKASJON.VERSJONID > IDENT.VERSJONID
      RENAME_SET_VALUE KVALITET.POSISJONSKVALITET.MÅLEMETODE > KVALITET.MÅLEMETODE
      RENAME_SET_VALUE KVALITET.POSISJONSKVALITET.NØYAKTIGHET > KVALITET.NØYAKTIGHET
      RENAME_SET_VALUE KVALITET.POSISJONSKVALITET.SYNBARHET > KVALITET.SYNBARHET
      RENAME_SET_VALUE KVALITET.POSISJONSKVALITET.MÅLEMETODEHØYDE > KVALITET.MÅLEMETODEHØYDE
      RENAME_SET_VALUE KVALITET.POSISJONSKVALITET.NØYAKTIGHETHØYDE > KVALITET.NØYAKTIGHETHØYDE
      RENAME_SET_VALUE KVALITET.POSISJONSKVALITET.MAKSIMALTAVVIK > KVALITET.MAKSIMALTAVVIK
      RENAME_SET_VALUE MEDIUM
      RENAME_SET_VALUE STANDARDLRM > LRLRM
      RENAME_SET_VALUE DETALJNIVÅ
      SET_TO KONNEKTERINGSLENKE = FME_CONDITIONAL:DEFAULT_VALUE'_FME_NO_OP_'BOOL_OP;OR;COMPOSITE_TEST;<Unused>;TEST @Value(KONNEKTERINGSLENKE) = true'JA'BOOL_OP;OR;COMPOSITE_TEST;<Unused>;TEST @Value(KONNEKTERINGSLENKE) = false'NEI'FME_NUM_CONDITIONS3___
      RENAME_SET_VALUE VEGLENKEADRESSE.VEGLENKEADRESSE.ADRESSEKODE > VEGLENKEADRESSE.ADRESSEKODE
      RENAME_SET_VALUE VEGLENKEADRESSE.VEGLENKEADRESSE.ADRESSENAVN > VEGLENKEADRESSE.ADRESSENAVN
      RENAME_SET_VALUE VEGLENKEADRESSE.VEGLENKEADRESSE.SIDEVEG > VEGLENKEADRESSE.SIDEVEG = FME_CONDITIONAL:DEFAULT_VALUE'_FME_NO_OP_'BOOL_OP;OR;COMPOSITE_TEST;<Unused>;TEST @Value(VEGLENKEADRESSE.SIDEVEG) = true'JA'BOOL_OP;OR;COMPOSITE_TEST;<Unused>;TEST @Value(VEGLENKEADRESSE.SIDEVEG) = false'NEI'FME_NUM_CONDITIONS3___
      REMOVE SENTERLINJE
      RENAME_SET_VALUE LINEÆRPOSISJONSTREKNING.FRAPOSISJON > LRSTREKNING.LRFRAPOSISJON
      RENAME_SET_VALUE LINEÆRPOSISJONSTREKNING.TILPOSISJON > LRSTREKNING.LRTILPOSISJON
      REMOVE _ELEMENT_INDEX
      RENAME_SET_VALUE VARETRANSPORTHVERDAGULØRDAGPERIODE1FRAKL > VARETRANSPORT_HVERDAG_1_FRA
      RENAME_SET_VALUE VARETRANSPORTHVERDAGULØRDAGPERIODE1TILKL > VARETRANSPORT_HVERDAG_1_TIL
      RENAME_SET_VALUE VARETRANSPORTHVERDAGULØRDAGPERIODE2FRAKL > VARETRANSPORT_HVERDAG_2_FRA
      RENAME_SET_VALUE VARETRANSPORTHVERDAGULØRDAGPERIODE2TILKL > VARETRANSPORT_HVERDAG_2_TIL
      RENAME_SET_VALUE KJØRINGTILEIENDOMMENETILLATT > KJØRING_TIL_EIENDOM_TILLAT
      RENAME_SET_VALUE LINEÆRPOSISJONPUNKT.POSISJON > LRPUNKT.LRPUNKTPOSISJON
      RENAME_SET_VALUE SVINGEFORBUDFRA.LINEÆRPOSISJONPUNKT.POSISJON > SVINGEFORBUDFRA.LRPUNKTPOSISJON
      RENAME_SET_VALUE SVINGEFORBUDTIL.LINEÆRPOSISJONPUNKT.POSISJON > SVINGEFORBUDTIL.LRPUNKTPOSISJON
      SET_TO LRPOSISJON.LRLRM = FME_CONDITIONAL:DEFAULT_VALUE'_FME_NO_OP_'BOOL_OP;OR;COMPOSITE_TEST;<Unused>;TEST @Value(LRPOSISJON.LRLRM) = metrering'1'BOOL_OP;OR;COMPOSITE_TEST;<Unused>;TEST @Value(LRPOSISJON.LRLRM) = kilometrering'2'BOOL_OP;OR;COMPOSITE_TEST;<Unused>;TEST @Value(LRPOSISJON.LRLRM) = normalisert'3'BOOL_OP;OR;COMPOSITE_TEST;<Unused>;TEST @Value(LRPOSISJON.LRLRM) = prosent'5'FME_NUM_CONDITIONS5___
      RENAME_SET_VALUE KOMMUNENUMMER > KOMM
      RENAME_SET_VALUE LENKESEKVENS.LENKESEKVENSREFERANSE.IDENTIFIKASJON.IDENTIFIKASJON.LOKALID > LENKESEKVENS.IDENT.LOKALID
      RENAME_SET_VALUE LENKESEKVENS.LENKESEKVENSREFERANSE.IDENTIFIKASJON.IDENTIFIKASJON.NAVNEROM > LENKESEKVENS.IDENT.NAVNEROM
      RENAME_SET_VALUE LENKESEKVENS.LENKESEKVENSREFERANSE.IDENTIFIKASJON.IDENTIFIKASJON.VERSJONID > LENKESEKVENS.IDENT.VERSJONID
      RENAME_SET_VALUE LENKESEKVENS.LENKESEKVENSREFERANSE.STARTPOSISJON > LENKESEKVENS.LRSTARTVERDI
      RENAME_SET_VALUE LENKESEKVENS.LENKESEKVENSREFERANSE.SLUTTPOSISJON > LENKESEKVENS.LRSLUTTVERDI
      RENAME_SET_VALUE OPPDATERINGSDATO
      RENAME_SET_VALUE VEDTAKSNUMMER
      RENAME_SET_VALUE GYLDIGFRADATO
      RENAME_SET_VALUE ARKIVNUMMER
      RENAME_SET_VALUE LINEÆRPOSISJONSTREKNING.FELT > LRSTREKNING.LRFELT
      RENAME_SET_VALUE LINEÆRPOSISJONSTREKNING.SIDEPOSISJON > LRSTREKNING.SIDEPOSISJON
      RENAME_SET_VALUE LINEÆRPOSISJONSTREKNING.HØYDEPOSISJON > LRSTREKNING.HØYDEPOSISJON
      RENAME_SET_VALUE VEGSYSTEMREFERANSE.VEGSYSTEMREFERANSE.VEGSYSTEM.VEGSYSTEM.VEGKATEGORI > VEGSYSTEMREFERANSE.VEGSYSTEM.VEGKATEGORI
      RENAME_SET_VALUE VEGSYSTEMREFERANSE.VEGSYSTEMREFERANSE.VEGSYSTEM.VEGSYSTEM.FASE > VEGSYSTEMREFERANSE.VEGSYSTEM.VEGFASE
      RENAME_SET_VALUE VEGSYSTEMREFERANSE.VEGSYSTEMREFERANSE.VEGSYSTEM.VEGSYSTEM.VEGNUMMER > VEGSYSTEMREFERANSE.VEGSYSTEM.VEGNUMMER
      RENAME_SET_VALUE VEGSYSTEMREFERANSE.VEGSYSTEMREFERANSE.VEGSTREKNING.VEGSTREKNING.STREKNINGNUMMER > VEGSYSTEMREFERANSE.VEGSTREKNING.STREKNINGNUMMER
      RENAME_SET_VALUE VEGSYSTEMREFERANSE.VEGSYSTEMREFERANSE.VEGSTREKNING.VEGSTREKNING.DELSTREKNINGNUMMER > VEGSYSTEMREFERANSE.VEGSTREKNING.DELSTREKNINGNUMMER
      RENAME_SET_VALUE VEGSYSTEMREFERANSE.VEGSYSTEMREFERANSE.VEGSTREKNING.VEGSTREKNING.FRAMETER > VEGSYSTEMREFERANSE.VEGSTREKNING.FRAMETER
      RENAME_SET_VALUE VEGSYSTEMREFERANSE.VEGSYSTEMREFERANSE.VEGSTREKNING.VEGSTREKNING.TILMETER > VEGSYSTEMREFERANSE.VEGSTREKNING.TILMETER
      RENAME_SET_VALUE VEGSYSTEMREFERANSE.VEGSYSTEMREFERANSE.VEGSTREKNING.VEGSTREKNING.ADSKILTELØP > VEGSYSTEMREFERANSE.VEGSTREKNING.ADSKILTELØP
      RENAME_SET_VALUE VEGSYSTEMREFERANSE.VEGSYSTEMREFERANSE.VEGSTREKNING.VEGSTREKNING.ADSKILTELØPNUMMER > VEGSYSTEMREFERANSE.VEGSTREKNING.ADSKILTELØPNUMMER
      RENAME_SET_VALUE VEGSYSTEMREFERANSE.VEGSYSTEMREFERANSE.SIDEANLEGG.SIDEANLEGG.SIDEANLEGGSDEL > VEGSYSTEMREFERANSE.SIDEANLEGG.SIDEANLEGGSDEL
      RENAME_SET_VALUE VEGSYSTEMREFERANSE.VEGSYSTEMREFERANSE.SIDEANLEGG.SIDEANLEGG.FRAMETER > VEGSYSTEMREFERANSE.SIDEANLEGG.FRAMETER
      RENAME_SET_VALUE VEGSYSTEMREFERANSE.VEGSYSTEMREFERANSE.SIDEANLEGG.SIDEANLEGG.TILMETER > VEGSYSTEMREFERANSE.SIDEANLEGG.TILMETER
      RENAME_SET_VALUE VEGSYSTEMREFERANSE.VEGSYSTEMREFERANSE.KRYSSYSTEM.KRYSSYSTEM.KRYSSDEL > VEGSYSTEMREFERANSE.KRYSSYSTEM.KRYSSDEL
      RENAME_SET_VALUE VEGSYSTEMREFERANSE.VEGSYSTEMREFERANSE.KRYSSYSTEM.KRYSSYSTEM.FRAMETER > VEGSYSTEMREFERANSE.KRYSSYSTEM.FRAMETER
      RENAME_SET_VALUE VEGSYSTEMREFERANSE.VEGSYSTEMREFERANSE.KRYSSYSTEM.KRYSSYSTEM.TILMETER > VEGSYSTEMREFERANSE.KRYSSYSTEM.TILMETER
      RENAME_SET_VALUE VEGSYSTEMREFERANSE.VEGSYSTEMREFERANSE.REFERANSERETNING > VEGSYSTEMREFERANSE.REFERANSERETNING
      RENAME_SET_VALUE SVINGEFORBUDFRA.LINEÆRPOSISJONPUNKT.FELT > SVINGEFORBUDFRA.LRFELT
      RENAME_SET_VALUE SVINGEFORBUDFRA.LINEÆRPOSISJONPUNKT.SIDEPOSISJON > SVINGEFORBUDFRA.LRSIDEPOSISJON
      RENAME_SET_VALUE SVINGEFORBUDFRA.LINEÆRPOSISJONPUNKT.HØYDEPOSISJON > SVINGEFORBUDFRA.LRHØYDEPOSISJON
      RENAME_SET_VALUE SVINGEFORBUDTIL.LINEÆRPOSISJONPUNKT.FELT > SVINGEFORBUDTIL.LRFELT
      RENAME_SET_VALUE SVINGEFORBUDTIL.LINEÆRPOSISJONPUNKT.SIDEPOSISJON > SVINGEFORBUDTIL.LRSIDEPOSISJON
      RENAME_SET_VALUE SVINGEFORBUDTIL.LINEÆRPOSISJONPUNKT.HØYDEPOSISJON > SVINGEFORBUDTIL.LRHØYDEPOSISJON
      RENAME_SET_VALUE LINEÆRPOSISJONPUNKT.FELT > LRPUNKT.LRFELT
      RENAME_SET_VALUE LINEÆRPOSISJONPUNKT.SIDEPOSISJON > LRPUNKT.SIDEPOSISJON
      RENAME_SET_VALUE LINEÆRPOSISJONPUNKT.HØYDEPOSISJON > LRPUNKT.HØYDEPOSISJON
      RENAME_SET_VALUE LINEÆRPOSISJONSTREKNING.LINEÆRREFERANSEMETODE > LRSTREKNING.LRLRM
      RENAME_SET_VALUE LINEÆRPOSISJONSTREKNING.RETNING > LRSTREKNING.RETNING
      RENAME_SET_VALUE LINEÆRPOSISJONSTREKNING.AVSTANDSIDE > LRSTREKNING.AVSTANDSIDE
      RENAME_SET_VALUE LINEÆRPOSISJONSTREKNING.LENKESEKVENS.IDENTIFIKASJON.LOKALID > LRSTREKNING.IDENT.LOKALID
      RENAME_SET_VALUE LINEÆRPOSISJONSTREKNING.LENKESEKVENS.IDENTIFIKASJON.NAVNEROM > LRSTREKNING.IDENT.NAVNEROM
      RENAME_SET_VALUE LINEÆRPOSISJONSTREKNING.LENKESEKVENS.IDENTIFIKASJON.VERSJONID > LRSTREKNING.IDENT.VERSJONID
      SET_TO LRSTREKNING.LRLRM = FME_CONDITIONAL:DEFAULT_VALUE'_FME_NO_OP_'BOOL_OP;OR;COMPOSITE_TEST;<Unused>;TEST @Value(LRPOSISJON.LRLRM) = metrering'1'BOOL_OP;OR;COMPOSITE_TEST;<Unused>;TEST @Value(LRPOSISJON.LRLRM) = kilometrering'2'BOOL_OP;OR;COMPOSITE_TEST;<Unused>;TEST @Value(LRPOSISJON.LRLRM) = normalisert'3'BOOL_OP;OR;COMPOSITE_TEST;<Unused>;TEST @Value(LRPOSISJON.LRLRM) = prosent'5'FME_NUM_CONDITIONS5___
      RENAME_SET_VALUE LINEÆRPOSISJONPUNKT.LINEÆRREFERANSEMETODE > LRPUNKT.LRLRM
      RENAME_SET_VALUE LINEÆRPOSISJONPUNKT.RETNING > LRPUNKT.RETNING
      RENAME_SET_VALUE LINEÆRPOSISJONPUNKT.AVSTANDSIDE > LRPUNKT.AVSTANDSIDE
      RENAME_SET_VALUE LINEÆRPOSISJONPUNKT.LENKESEKVENS.IDENTIFIKASJON.LOKALID > LRPUNKT.IDENT.LOKALID
      RENAME_SET_VALUE LINEÆRPOSISJONPUNKT.LENKESEKVENS.IDENTIFIKASJON.NAVNEROM > LRPUNKT.IDENT.NAVNEROM
      RENAME_SET_VALUE LINEÆRPOSISJONPUNKT.LENKESEKVENS.IDENTIFIKASJON.VERSJONID > LRPUNKT.IDENT.VERSJONID
      RENAME_SET_VALUE SVINGEFORBUDFRA.LINEÆRPOSISJONPUNKT.LINEÆRREFERANSEMETODE > SVINGEFORBUDFRA.LRLRM
      RENAME_SET_VALUE SVINGEFORBUDFRA.LINEÆRPOSISJONPUNKT.RETNING > SVINGEFORBUDFRA.RETNING
      RENAME_SET_VALUE SVINGEFORBUDFRA.LINEÆRPOSISJONPUNKT.AVSTANDSIDE > SVINGEFORBUDFRA.LRAVSTANDSIDE
      RENAME_SET_VALUE SVINGEFORBUDFRA.LINEÆRPOSISJONPUNKT.LENKESEKVENS.IDENTIFIKASJON.LOKALID > SVINGEFORBUDFRA.IDENT.LOKALID
      RENAME_SET_VALUE SVINGEFORBUDFRA.LINEÆRPOSISJONPUNKT.LENKESEKVENS.IDENTIFIKASJON.NAVNEROM > SVINGEFORBUDFRA.IDENT.NAVNEROM
      RENAME_SET_VALUE SVINGEFORBUDFRA.LINEÆRPOSISJONPUNKT.LENKESEKVENS.IDENTIFIKASJON.VERSJONID > SVINGEFORBUDFRA.IDENT.VERSJONID
      RENAME_SET_VALUE SVINGEFORBUDTIL.LINEÆRPOSISJONPUNKT.LINEÆRREFERANSEMETODE > SVINGEFORBUDTIL.LRLRM
      RENAME_SET_VALUE SVINGEFORBUDTIL.LINEÆRPOSISJONPUNKT.RETNING > SVINGEFORBUDTIL.RETNING
      RENAME_SET_VALUE SVINGEFORBUDTIL.LINEÆRPOSISJONPUNKT.AVSTANDSIDE > SVINGEFORBUDTIL.LRAVSTANDSIDE
      RENAME_SET_VALUE SVINGEFORBUDTIL.LINEÆRPOSISJONPUNKT.LENKESEKVENS.IDENTIFIKASJON.LOKALID > SVINGEFORBUDTIL.IDENT.LOKALID
      RENAME_SET_VALUE SVINGEFORBUDTIL.LINEÆRPOSISJONPUNKT.LENKESEKVENS.IDENTIFIKASJON.NAVNEROM > SVINGEFORBUDTIL.IDENT.NAVNEROM
      RENAME_SET_VALUE SVINGEFORBUDTIL.LINEÆRPOSISJONPUNKT.LENKESEKVENS.IDENTIFIKASJON.VERSJONID > SVINGEFORBUDTIL.IDENT.VERSJONID
    -> GeometryFilter
GeometryFilter
    BREAK_AGG = No
    GEOM_PORT_NAMES = Point Line Null Instance
    POINT -> 3DForcer
    LINE -> 3DForcer
    NULL -> DateFormatter
3DForcer
    KEEPZVAL = Yes
    ZVALATTR = -999999
    -> GeometryExtractor
GeometryExtractor
    ATTR = _wkt
    KIND_LONG = OGC Well Known Text
    OGCVERSION = 1.2
    OGC_WKT_PRECISION_DISPLAY = 64-bit
    PREFER_POLYGON_OVER_SURFACE = No
    REMOVE_GEOMETRY = No
    -> StringReplacer
StringReplacer
    CASE = NO
    FIND_TEXT = nan
    NO_MATCH = _FME_NO_OP_
    REGEXP = NO
    REPLACE_TEXT = 2500
    SRC_ATTRS = _wkt
    -> StringReplacer_2
StringReplacer_2
    CASE = NO
    FIND_TEXT = -999999
    NO_MATCH = _FME_NO_OP_
    REGEXP = NO
    REPLACE_TEXT = 2500
    SRC_ATTRS = _wkt
    -> GeometryReplacer
GeometryReplacer
    KIND_LONG = OGC Well Known Text
    OGC_WKT_PRECISION_DISPLAY = 64-bit
    REMOVE_ATTRIBUTE = Yes
    SOURCE = @Value(_wkt)
    -> DateFormatter
DateFormatter
    DATE_ATTR = VERIFISERINGSDATO,GYLDIGFRADATO,DATOTIL,MÅLEDATO,OPPDATERINGSDATO,DATOFRA,DATAFANGSTDATO
    FMT = %Y%m%d
    INVALID_DATE_VALUE = _FME_NO_OP_
    SRCFMT = Unknown - Automatic Detection
    -> Veglenke (writer GDMMAPPERSOSI_1)
    -> FeatureWriter [Output]
    -> FeatureWriter_2 [Output]
Veglenke (writer GDMMAPPERSOSI_1) [off]
    attributes: IDENT.LOKALID varchar(200), IDENT.NAVNEROM varchar(200), IDENT.VERSJONID varchar(200), DATAFANGSTDATO varchar(200), KVALITET.MÅLEMETODE varchar(200), KVALITET.NØYAKTIGHET varchar(200), KVALITET.SYNBARHET varchar(200), KVALITET.MÅLEMETODEHØYDE varchar(200), KVALITET.NØYAKTIGHETHØYDE varchar(200), KVALITET.MAKSIMALTAVVIK varchar(200), MEDIUM varchar(200), LRLRM varchar(200), DETALJNIVÅ varchar(200), FELTOVERSIKT varchar(200), KONNEKTERINGSLENKE varchar(200), TYPEVEG varchar(200), VEGLENKEADRESSE.ADRESSEKODE varchar(200), VEGLENKEADRESSE.ADRESSENAVN varchar(200), VEGLENKEADRESSE.SIDEVEG varchar(200), FARTSGRENSEVERDI varchar(200), LRSTREKNING.LRFRAPOSISJON varchar(200), LRSTREKNING.LRTILPOSISJON varchar(200), VEGKLASSE varchar(200), VARETRANSPORT_HVERDAG_1_FRA varchar(200), VARETRANSPORT_HVERDAG_1_TIL varchar(200), VARETRANSPORT_HVERDAG_2_FRA varchar(200), VARETRANSPORT_HVERDAG_2_TIL varchar(200), KJØRING_TIL_EIENDOM_TILLAT varchar(200), KLASSELANDBRUKSVEG varchar(200), TYPEJERNBANEKRYSSING varchar(200),
      POSISJON varchar(200), LRPUNKT.LRPUNKTPOSISJON varchar(200), HØYFJELLSSTREKNING varchar(200), VINTERSTENGT_FRADATO varchar(200), VINTERSTENGT_TILDATO varchar(200), HOVEDPROBLEM varchar(200), SKILTAHØYDE varchar(200), TRAFIKKREGULERINGER varchar(200), TYPE varchar(200), SVINGEFORBUDFRA.LRPUNKTPOSISJON varchar(200), SVINGEFORBUDTIL.LRPUNKTPOSISJON varchar(200), fme_rejection_code varchar(200), LRPOSISJON.LRLRM varchar(200), KOMM varchar(200), LENKESEKVENS.IDENT.LOKALID varchar(200), LENKESEKVENS.IDENT.NAVNEROM varchar(200), LENKESEKVENS.IDENT.VERSJONID varchar(200), LENKESEKVENS.LRSTARTVERDI varchar(200), LENKESEKVENS.LRSLUTTVERDI varchar(200), GJENTAKELSESINTERVALL varchar(200), OPPDATERINGSDATO varchar(200), VEDTAKSNUMMER varchar(200), GYLDIGFRADATO varchar(200), ARKIVNUMMER varchar(200), LRSTREKNING.LRFELT varchar(200), LRSTREKNING.SIDEPOSISJON varchar(200), LRSTREKNING.HØYDEPOSISJON varchar(200), VERIFISERINGSDATO varchar(200), KOMMUNENUMMER.CODESPACE varchar(200), KVALITET.POSISJONSKVALITET.MÅLEMETODE.CODESPACE varchar(200),
      KVALITET.POSISJONSKVALITET.MÅLEMETODEHØYDE.CODESPACE varchar(200), VEGSYSTEMREFERANSE.VEGSYSTEM.VEGKATEGORI varchar(200), VEGSYSTEMREFERANSE.VEGSYSTEM.VEGFASE varchar(200), VEGSYSTEMREFERANSE.VEGSYSTEM.VEGNUMMER varchar(200), VEGSYSTEMREFERANSE.VEGSTREKNING.STREKNINGNUMMER varchar(200), VEGSYSTEMREFERANSE.VEGSTREKNING.DELSTREKNINGNUMMER varchar(200), VEGSYSTEMREFERANSE.VEGSTREKNING.FRAMETER varchar(200), VEGSYSTEMREFERANSE.VEGSTREKNING.TILMETER varchar(200), VEGSYSTEMREFERANSE.VEGSTREKNING.ADSKILTELØP varchar(200), VEGSYSTEMREFERANSE.VEGSTREKNING.ADSKILTELØPNUMMER varchar(200), VEGSYSTEMREFERANSE.SIDEANLEGG.SIDEANLEGGSDEL varchar(200), VEGSYSTEMREFERANSE.SIDEANLEGG.FRAMETER varchar(200), VEGSYSTEMREFERANSE.SIDEANLEGG.TILMETER varchar(200), VEGSYSTEMREFERANSE.KRYSSYSTEM.KRYSSDEL varchar(200), VEGSYSTEMREFERANSE.KRYSSYSTEM.FRAMETER varchar(200), VEGSYSTEMREFERANSE.KRYSSYSTEM.TILMETER varchar(200), VEGSYSTEMREFERANSE.REFERANSERETNING varchar(200), MERKNAD varchar(200), SVINGEFORBUDFRA.LRFELT varchar(200), SVINGEFORBUDFRA.LRSIDEPOSISJON varchar(200), SVINGEFORBUDFRA.LRHØYDEPOSISJON varchar(200), SVINGEFORBUDTIL.LRFELT varchar(200), SVINGEFORBUDTIL.LRSIDEPOSISJON varchar(200), SVINGEFORBUDTIL.LRHØYDEPOSISJON varchar(200), UKEDAG varchar(200), DATOFRA varchar(200), DATOTIL varchar(200), KLOKKESLETTFRA varchar(200), KLOKKESLETTTIL varchar(200), PROSJEKTREFERANSE varchar(200),
      MOTORVEGTYPE varchar(200), SKILTNUMMER varchar(200), NAVN varchar(200), STEDLIGBEREDSKAP varchar(200), SNØDYBDE varchar(200), ANTALLSTENGTEDØGN varchar(200), NATTESTENGT_FRADATO varchar(200), NATTESTENGT_TILDATO varchar(200), AVGRENSAVINTERDRIFTFRADATO varchar(200), AVGRENSAVINTERDRIFTTILDATO varchar(200), TERSKELVERDI varchar(200), KILDE varchar(200), TILLEGGSINFORMASJON varchar(200), GJELDERTIDSROM varchar(200), VARETRANSPORTLØRDAGPERIODE1FRAKL varchar(200), VARETRANSPORTLØRDAGPERIODE1TILKL varchar(200), VARETRANSPORTLØRDAGPERIODE2FRAKL varchar(200), VARETRANSPORTLØRDAGPERIODE2TILKL varchar(200), FUNKSJON varchar(200), EIER varchar(200), LRPUNKT.LRFELT varchar(200), LRPUNKT.SIDEPOSISJON varchar(200), LRPUNKT.HØYDEPOSISJON varchar(200), TYPEHINDER varchar(200), BEREGNETHØYDE varchar(200), BREDDE varchar(200), HMINHØYREKANT varchar(200), HMINMIDT varchar(200), HMINVENSTREKANT varchar(200), MÅLEMETODE varchar(200),
      MÅLEDATO varchar(200), LRSTREKNING.RETNING varchar(200), LRSTREKNING.AVSTANDSIDE varchar(200), LRSTREKNING.IDENT.LOKALID varchar(200), LRSTREKNING.IDENT.NAVNEROM varchar(200), LRSTREKNING.IDENT.VERSJONID varchar(200), LRSTREKNING.LRLRM varchar(200), LRPUNKT.LRLRM varchar(200), LRPUNKT.RETNING varchar(200), LRPUNKT.AVSTANDSIDE varchar(200), LRPUNKT.IDENT.LOKALID varchar(200), LRPUNKT.IDENT.NAVNEROM varchar(200), LRPUNKT.IDENT.VERSJONID varchar(200), SVINGEFORBUDFRA.LRLRM varchar(200), SVINGEFORBUDFRA.RETNING varchar(200), SVINGEFORBUDFRA.LRAVSTANDSIDE varchar(200), SVINGEFORBUDFRA.IDENT.LOKALID varchar(200), SVINGEFORBUDFRA.IDENT.NAVNEROM varchar(200), SVINGEFORBUDFRA.IDENT.VERSJONID varchar(200), SVINGEFORBUDTIL.LRLRM varchar(200), SVINGEFORBUDTIL.RETNING varchar(200), SVINGEFORBUDTIL.LRAVSTANDSIDE varchar(200), SVINGEFORBUDTIL.IDENT.LOKALID varchar(200), SVINGEFORBUDTIL.IDENT.NAVNEROM varchar(200), SVINGEFORBUDTIL.IDENT.VERSJONID varchar(200)
FeatureWriter
    DATASET = $(mainFolder)\GML\kommune\$(kommune)\@Value(fme_feature_type).sos
    DATASET_ATTR = _dataset
    FEATURE_TYPE_LIST_ATTR = _feature_type
    FORMAT = GDMMAPPERSOSI
    GDMMAPPERSOSI_GDMW_CONVERTARCTOVECTORS = yes
    GDMMAPPERSOSI_GDMW_IGNOREATTRIBUTENAMES = fme;autocad
    GDMMAPPERSOSI_GDMW_OBJTYPEFORGENERATEDCURVES = KantUtsnitt
    GDMMAPPERSOSI_GDMW_SOSIUNIT = 0.01
    GDMMAPPERSOSI_GDMW_SOSIVERSION = 5.0
    GDMMAPPERSOSI_GDMW_SOSI_CHARSET = UTF-8
    GDMMAPPERSOSI_GDMW_SOSI_OVERRIDE_SOURCESHEADPARAMS = no
    GDMMAPPERSOSI_GDMW_SOSI_OWNER = Statens vegvesen/Statens kartverk/Kommunene
    GDMMAPPERSOSI_GDMW_SOSI_PRODUCEDBY = Elveg 2.0
    GDMMAPPERSOSI_GDMW_SOSI_VERTICALDATUM = NN2000-Nytt_felles_nordisk_vertikalt_datum,_basert_på_Normaal_Amsterdams_Peil.
    GDMMAPPERSOSI_GDMW_STOREFMESURFACEASGDMPOINT = no
    GDMMAPPERSOSI_GDMW_STORETOPOLOGY = no
    GDMMAPPERSOSI_GDMW_TEMPPATH = C:\DATA\GIT\SOSI-Vegnett\tmp
    GDMMAPPERSOSI_GDMW_USETYPEREGONWRITE = NO
    GDMMAPPERSOSI_GDMW_WRITETHEMECODE = no
    TOTAL_FEATURES_WRITTEN_ATTR = _total_features_written
    SUMMARY -> PythonCaller_postProcessSOSI
FeatureWriter_2
    DATASET = $(mainFolder)\GML\kommune\$(kommune).sos
    DATASET_ATTR = _dataset
    FEATURE_TYPE_LIST_ATTR = _feature_type
    FORMAT = GDMMAPPERSOSI
    GDMMAPPERSOSI_GDMW_CONVERTARCTOVECTORS = yes
    GDMMAPPERSOSI_GDMW_IGNOREATTRIBUTENAMES = fme;autocad
    GDMMAPPERSOSI_GDMW_OBJTYPEFORGENERATEDCURVES = KantUtsnitt
    GDMMAPPERSOSI_GDMW_SOSIUNIT = 0.01
    GDMMAPPERSOSI_GDMW_SOSIVERSION = 5.0
    GDMMAPPERSOSI_GDMW_SOSI_CHARSET = UTF-8
    GDMMAPPERSOSI_GDMW_SOSI_OVERRIDE_SOURCESHEADPARAMS = no
    GDMMAPPERSOSI_GDMW_SOSI_OWNER = Statens vegvesen/Statens kartverk/Kommunene
    GDMMAPPERSOSI_GDMW_SOSI_PRODUCEDBY = Elveg 2.0
    GDMMAPPERSOSI_GDMW_SOSI_VERTICALDATUM = NN2000-Nytt_felles_nordisk_vertikalt_datum,_basert_på_Normaal_Amsterdams_Peil.
    GDMMAPPERSOSI_GDMW_STOREFMESURFACEASGDMPOINT = no
    GDMMAPPERSOSI_GDMW_STORETOPOLOGY = no
    GDMMAPPERSOSI_GDMW_TEMPPATH = C:\DATA\GIT\SOSI-Vegnett\tmp
    GDMMAPPERSOSI_GDMW_USETYPEREGONWRITE = NO
    GDMMAPPERSOSI_GDMW_WRITETHEMECODE = no
    TOTAL_FEATURES_WRITTEN_ATTR = _total_features_written
    SUMMARY -> PythonCaller_postProcessSOSI
PythonCaller_postProcessSOSI [off]
    PYTHONSOURCE:
      import fme
      import fmeobjects
      # Template Function interface:
      # When using this function, make sure its name is set as the value of
      # the 'Class or Function to Process Features' transformer parameter
      def processFeature(feature):
          file_location = feature.getAttribute('_dataset')
          if file_location:
              postProcessSOSI(file_location)
    PYTHONSYMBOL = processFeature

Bookmark: New Bookmark
Veglenke (reader GML_1)
    attributes: identifikasjon.Identifikasjon.lokalId xml_buffer, identifikasjon.Identifikasjon.navnerom xml_buffer, identifikasjon.Identifikasjon.versjonId xml_buffer, oppdateringsdato xml_datetime, datafangstdato xml_date, verifiseringsdato xml_date, kommunenummer xml_buffer, kommunenummer.codeSpace xml_buffer, kvalitet.Posisjonskvalitet.målemetode xml_buffer, kvalitet.Posisjonskvalitet.målemetode.codeSpace xml_buffer, kvalitet.Posisjonskvalitet.nøyaktighet xml_int64, kvalitet.Posisjonskvalitet.synbarhet xml_buffer, kvalitet.Posisjonskvalitet.målemetodeHøyde xml_buffer, kvalitet.Posisjonskvalitet.målemetodeHøyde.codeSpace xml_buffer, kvalitet.Posisjonskvalitet.nøyaktighetHøyde xml_int64, kvalitet.Posisjonskvalitet.maksimaltAvvik xml_int64, medium xml_buffer, standardLRM xml_buffer, lenkesekvens.Lenkesekvensreferanse.identifikasjon.Identifikasjon.lokalId xml_buffer, lenkesekvens.Lenkesekvensreferanse.identifikasjon.Identifikasjon.navnerom xml_buffer, lenkesekvens.Lenkesekvensreferanse.identifikasjon.Identifikasjon.versjonId xml_buffer, lenkesekvens.Lenkesekvensreferanse.startposisjon xml_real64, lenkesekvens.Lenkesekvensreferanse.sluttposisjon xml_real64, typeVeg xml_buffer, detaljnivå xml_buffer, konnekteringslenke xml_boolean, veglenkeadresse.Veglenkeadresse.adressekode xml_int64, veglenkeadresse.Veglenkeadresse.adressenavn xml_buffer, veglenkeadresse.Veglenkeadresse.sideveg xml_buffer, vegsystemreferanse.Vegsystemreferanse.vegsystem.Vegsystem.vegkategori xml_buffer,
      vegsystemreferanse.Vegsystemreferanse.vegsystem.Vegsystem.fase xml_buffer, vegsystemreferanse.Vegsystemreferanse.vegsystem.Vegsystem.vegnummer xml_int64, vegsystemreferanse.Vegsystemreferanse.vegstrekning.Vegstrekning.strekningNummer xml_int64, vegsystemreferanse.Vegsystemreferanse.vegstrekning.Vegstrekning.delstrekningNummer xml_int64, vegsystemreferanse.Vegsystemreferanse.vegstrekning.Vegstrekning.fraMeter xml_int64, vegsystemreferanse.Vegsystemreferanse.vegstrekning.Vegstrekning.tilMeter xml_int64, vegsystemreferanse.Vegsystemreferanse.vegstrekning.Vegstrekning.adskilteLøp xml_buffer, vegsystemreferanse.Vegsystemreferanse.vegstrekning.Vegstrekning.adskilteLøpNummer xml_buffer, vegsystemreferanse.Vegsystemreferanse.sideanlegg.Sideanlegg.sideanleggsdel xml_int64, vegsystemreferanse.Vegsystemreferanse.sideanlegg.Sideanlegg.fraMeter xml_int64, vegsystemreferanse.Vegsystemreferanse.sideanlegg.Sideanlegg.tilMeter xml_int64, vegsystemreferanse.Vegsystemreferanse.kryssystem.Kryssystem.kryssdel xml_int64, vegsystemreferanse.Vegsystemreferanse.kryssystem.Kryssystem.fraMeter xml_int64, vegsystemreferanse.Vegsystemreferanse.kryssystem.Kryssystem.tilMeter xml_int64, vegsystemreferanse.Vegsystemreferanse.referanseretning xml_buffer, feltoversikt xml_buffer, senterlinje xml_geometry
    -> BulkAttributeRenamer
Beredskapsveg (reader GML_1)
    attributes: identifikasjon.Identifikasjon.lokalId xml_buffer, identifikasjon.Identifikasjon.navnerom xml_buffer, identifikasjon.Identifikasjon.versjonId xml_buffer, oppdateringsdato xml_datetime, senterlinje xml_geometry, lineærPosisjon{}.LineærPosisjonStrekning.lineærReferanseMetode xml_buffer, lineærPosisjon{}.LineærPosisjonStrekning.retning xml_buffer, lineærPosisjon{}.LineærPosisjonStrekning.avstandSide xml_real64, lineærPosisjon{}.LineærPosisjonStrekning.lenkesekvens.Identifikasjon.lokalId xml_buffer, lineærPosisjon{}.LineærPosisjonStrekning.lenkesekvens.Identifikasjon.navnerom xml_buffer, lineærPosisjon{}.LineærPosisjonStrekning.lenkesekvens.Identifikasjon.versjonId xml_buffer, lineærPosisjon{}.LineærPosisjonStrekning.felt xml_buffer, lineærPosisjon{}.LineærPosisjonStrekning.sideposisjon xml_buffer, lineærPosisjon{}.LineærPosisjonStrekning.høydeposisjon xml_buffer, lineærPosisjon{}.LineærPosisjonStrekning.fraPosisjon xml_real64, lineærPosisjon{}.LineærPosisjonStrekning.tilPosisjon xml_real64
    -> ListExploder
Fartsgrense (reader GML_1)
    attributes: identifikasjon.Identifikasjon.lokalId xml_buffer, identifikasjon.Identifikasjon.navnerom xml_buffer, identifikasjon.Identifikasjon.versjonId xml_buffer, oppdateringsdato xml_datetime, fartsgrenseVerdi xml_buffer, vedtaksnummer xml_buffer, gyldigFraDato xml_date, arkivnummer xml_buffer, senterlinje xml_geometry, lineærPosisjon{}.LineærPosisjonStrekning.lineærReferanseMetode xml_buffer, lineærPosisjon{}.LineærPosisjonStrekning.retning xml_buffer, lineærPosisjon{}.LineærPosisjonStrekning.avstandSide xml_real64, lineærPosisjon{}.LineærPosisjonStrekning.lenkesekvens.Identifikasjon.lokalId xml_buffer, lineærPosisjon{}.LineærPosisjonStrekning.lenkesekvens.Identifikasjon.navnerom xml_buffer, lineærPosisjon{}.LineærPosisjonStrekning.lenkesekvens.Identifikasjon.versjonId xml_buffer, lineærPosisjon{}.LineærPosisjonStrekning.felt xml_buffer, lineærPosisjon{}.LineærPosisjonStrekning.sideposisjon xml_buffer, lineærPosisjon{}.LineærPosisjonStrekning.høydeposisjon xml_buffer, lineærPosisjon{}.LineærPosisjonStrekning.fraPosisjon xml_real64, lineærPosisjon{}.LineærPosisjonStrekning.tilPosisjon xml_real64
    -> ListExploder
FartsgrenseVariabel (reader GML_1)
    attributes: identifikasjon.Identifikasjon.lokalId xml_buffer, identifikasjon.Identifikasjon.navnerom xml_buffer, identifikasjon.Identifikasjon.versjonId xml_buffer, oppdateringsdato xml_datetime, fartsgrenseVerdi xml_buffer, type xml_buffer, ukedag xml_buffer, datoFra xml_buffer, datoTil xml_buffer, klokkeslettFra xml_buffer, klokkeslettTil xml_buffer, vedtaksnummer xml_buffer, gyldigFraDato xml_date, merknad xml_buffer, arkivnummer xml_buffer, prosjektreferanse xml_buffer, senterlinje xml_geometry, lineærPosisjon{}.LineærPosisjonStrekning.lineærReferanseMetode xml_buffer, lineærPosisjon{}.LineærPosisjonStrekning.retning xml_buffer, lineærPosisjon{}.LineærPosisjonStrekning.avstandSide xml_real64, lineærPosisjon{}.LineærPosisjonStrekning.lenkesekvens.Identifikasjon.lokalId xml_buffer, lineærPosisjon{}.LineærPosisjonStrekning.lenkesekvens.Identifikasjon.navnerom xml_buffer, lineærPosisjon{}.LineærPosisjonStrekning.lenkesekvens.Identifikasjon.versjonId xml_buffer, lineærPosisjon{}.LineærPosisjonStrekning.felt xml_buffer, lineærPosisjon{}.LineærPosisjonStrekning.sideposisjon xml_buffer, lineærPosisjon{}.LineærPosisjonStrekning.høydeposisjon xml_buffer, lineærPosisjon{}.LineærPosisjonStrekning.fraPosisjon xml_real64, lineærPosisjon{}.LineærPosisjonStrekning.tilPosisjon xml_real64
    -> ListExploder
FunksjonellVegklasse (reader GML_1)
    attributes: identifikasjon.Identifikasjon.lokalId xml_buffer, identifikasjon.Identifikasjon.navnerom xml_buffer, identifikasjon.Identifikasjon.versjonId xml_buffer, oppdateringsdato xml_datetime, vegklasse xml_buffer, merknad xml_buffer, senterlinje xml_geometry, lineærPosisjon{}.LineærPosisjonStrekning.lineærReferanseMetode xml_buffer, lineærPosisjon{}.LineærPosisjonStrekning.retning xml_buffer, lineærPosisjon{}.LineærPosisjonStrekning.avstandSide xml_real64, lineærPosisjon{}.LineærPosisjonStrekning.lenkesekvens.Identifikasjon.lokalId xml_buffer, lineærPosisjon{}.LineærPosisjonStrekning.lenkesekvens.Identifikasjon.navnerom xml_buffer, lineærPosisjon{}.LineærPosisjonStrekning.lenkesekvens.Identifikasjon.versjonId xml_buffer, lineærPosisjon{}.LineærPosisjonStrekning.felt xml_buffer, lineærPosisjon{}.LineærPosisjonStrekning.sideposisjon xml_buffer, lineærPosisjon{}.LineærPosisjonStrekning.høydeposisjon xml_buffer, lineærPosisjon{}.LineærPosisjonStrekning.fraPosisjon xml_real64, lineærPosisjon{}.LineærPosisjonStrekning.tilPosisjon xml_real64
    -> ListExploder
Gågatereguleringer (reader GML_1)
    attributes: identifikasjon.Identifikasjon.lokalId xml_buffer, identifikasjon.Identifikasjon.navnerom xml_buffer, identifikasjon.Identifikasjon.versjonId xml_buffer, oppdateringsdato xml_datetime, varetransportHverdagULørdagPeriode1FraKl xml_buffer, varetransportHverdagULørdagPeriode1TilKl xml_buffer, varetransportHverdagULørdagPeriode2FraKl xml_buffer, varetransportHverdagULørdagPeriode2TilKl xml_buffer, varetransportLørdagPeriode1FraKl xml_buffer, varetransportLørdagPeriode1TilKl xml_buffer, varetransportLørdagPeriode2FraKl xml_buffer, varetransportLørdagPeriode2TilKl xml_buffer, kjøringTilEiendommeneTillatt xml_buffer, senterlinje xml_geometry, lineærPosisjon{}.LineærPosisjonStrekning.lineærReferanseMetode xml_buffer, lineærPosisjon{}.LineærPosisjonStrekning.retning xml_buffer, lineærPosisjon{}.LineærPosisjonStrekning.avstandSide xml_real64, lineærPosisjon{}.LineærPosisjonStrekning.lenkesekvens.Identifikasjon.lokalId xml_buffer, lineærPosisjon{}.LineærPosisjonStrekning.lenkesekvens.Identifikasjon.navnerom xml_buffer, lineærPosisjon{}.LineærPosisjonStrekning.lenkesekvens.Identifikasjon.versjonId xml_buffer, lineærPosisjon{}.LineærPosisjonStrekning.felt xml_buffer, lineærPosisjon{}.LineærPosisjonStrekning.sideposisjon xml_buffer, lineærPosisjon{}.LineærPosisjonStrekning.høydeposisjon xml_buffer, lineærPosisjon{}.LineærPosisjonStrekning.fraPosisjon xml_real64, lineærPosisjon{}.LineærPosisjonStrekning.tilPosisjon xml_real64
    -> ListExploder
Høydebegrensning (reader GML_1)
    attributes: identifikasjon.Identifikasjon.lokalId xml_buffer, identifikasjon.Identifikasjon.navnerom xml_buffer, identifikasjon.Identifikasjon.versjonId xml_buffer, oppdateringsdato xml_datetime, skiltaHøyde xml_real64, typeHinder xml_buffer, beregnetHøyde xml_real64, navn xml_buffer, merknad xml_buffer, bredde xml_real64, hMinHøyreKant xml_real64, hMinMidt xml_real64, hMinVenstreKant xml_real64, målemetode xml_buffer, måledato xml_date, prosjektreferanse xml_buffer, senterlinje xml_geometry, lineærPosisjon{}.LineærPosisjonStrekning.lineærReferanseMetode xml_buffer, lineærPosisjon{}.LineærPosisjonStrekning.retning xml_buffer, lineærPosisjon{}.LineærPosisjonStrekning.avstandSide xml_real64, lineærPosisjon{}.LineærPosisjonStrekning.lenkesekvens.Identifikasjon.lokalId xml_buffer, lineærPosisjon{}.LineærPosisjonStrekning.lenkesekvens.Identifikasjon.navnerom xml_buffer, lineærPosisjon{}.LineærPosisjonStrekning.lenkesekvens.Identifikasjon.versjonId xml_buffer, lineærPosisjon{}.LineærPosisjonStrekning.felt xml_buffer, lineærPosisjon{}.LineærPosisjonStrekning.sideposisjon xml_buffer, lineærPosisjon{}.LineærPosisjonStrekning.høydeposisjon xml_buffer, lineærPosisjon{}.LineærPosisjonStrekning.fraPosisjon xml_real64, lineærPosisjon{}.LineærPosisjonStrekning.tilPosisjon xml_real64
    -> ListExploder
InnkjøringForbudt (reader GML_1)
    attributes: identifikasjon.Identifikasjon.lokalId xml_buffer, identifikasjon.Identifikasjon.navnerom xml_buffer, identifikasjon.Identifikasjon.versjonId xml_buffer, oppdateringsdato xml_datetime, merknad xml_buffer, skiltnummer xml_buffer, senterlinje xml_geometry, lineærPosisjon{}.LineærPosisjonStrekning.lineærReferanseMetode xml_buffer, lineærPosisjon{}.LineærPosisjonStrekning.retning xml_buffer, lineærPosisjon{}.LineærPosisjonStrekning.avstandSide xml_real64, lineærPosisjon{}.LineærPosisjonStrekning.lenkesekvens.Identifikasjon.lokalId xml_buffer, lineærPosisjon{}.LineærPosisjonStrekning.lenkesekvens.Identifikasjon.navnerom xml_buffer, lineærPosisjon{}.LineærPosisjonStrekning.lenkesekvens.Identifikasjon.versjonId xml_buffer, lineærPosisjon{}.LineærPosisjonStrekning.felt xml_buffer, lineærPosisjon{}.LineærPosisjonStrekning.sideposisjon xml_buffer, lineærPosisjon{}.LineærPosisjonStrekning.høydeposisjon xml_buffer, lineærPosisjon{}.LineærPosisjonStrekning.fraPosisjon xml_real64, lineærPosisjon{}.LineærPosisjonStrekning.tilPosisjon xml_real64
    -> ListExploder
Landbruksvegklasse (reader GML_1)
    attributes: identifikasjon.Identifikasjon.lokalId xml_buffer, identifikasjon.Identifikasjon.navnerom xml_buffer, identifikasjon.Identifikasjon.versjonId xml_buffer, oppdateringsdato xml_datetime, klasseLandbruksveg xml_buffer, senterlinje xml_geometry, lineærPosisjon{}.LineærPosisjonStrekning.lineærReferanseMetode xml_buffer, lineærPosisjon{}.LineærPosisjonStrekning.retning xml_buffer, lineærPosisjon{}.LineærPosisjonStrekning.avstandSide xml_real64, lineærPosisjon{}.LineærPosisjonStrekning.lenkesekvens.Identifikasjon.lokalId xml_buffer, lineærPosisjon{}.LineærPosisjonStrekning.lenkesekvens.Identifikasjon.navnerom xml_buffer, lineærPosisjon{}.LineærPosisjonStrekning.lenkesekvens.Identifikasjon.versjonId xml_buffer, lineærPosisjon{}.LineærPosisjonStrekning.felt xml_buffer, lineærPosisjon{}.LineærPosisjonStrekning.sideposisjon xml_buffer, lineærPosisjon{}.LineærPosisjonStrekning.høydeposisjon xml_buffer, lineærPosisjon{}.LineærPosisjonStrekning.fraPosisjon xml_real64, lineærPosisjon{}.LineærPosisjonStrekning.tilPosisjon xml_real64
    -> ListExploder
Jernbanekryssing (reader GML_1)
    attributes: identifikasjon.Identifikasjon.lokalId xml_buffer, identifikasjon.Identifikasjon.navnerom xml_buffer, identifikasjon.Identifikasjon.versjonId xml_buffer, oppdateringsdato xml_datetime, typeJernbanekryssing xml_buffer, tilleggsinformasjon xml_buffer, posisjon xml_geometry, lineærPosisjon.LineærPosisjonPunkt.lineærReferanseMetode xml_buffer, lineærPosisjon.LineærPosisjonPunkt.retning xml_buffer, lineærPosisjon.LineærPosisjonPunkt.avstandSide xml_real64, lineærPosisjon.LineærPosisjonPunkt.lenkesekvens.Identifikasjon.lokalId xml_buffer, lineærPosisjon.LineærPosisjonPunkt.lenkesekvens.Identifikasjon.navnerom xml_buffer, lineærPosisjon.LineærPosisjonPunkt.lenkesekvens.Identifikasjon.versjonId xml_buffer, lineærPosisjon.LineærPosisjonPunkt.felt xml_buffer, lineærPosisjon.LineærPosisjonPunkt.sideposisjon xml_buffer, lineærPosisjon.LineærPosisjonPunkt.høydeposisjon xml_buffer, lineærPosisjon.LineærPosisjonPunkt.posisjon xml_real64
    -> ListExploder
Motorveg (reader GML_1)
    attributes: identifikasjon.Identifikasjon.lokalId xml_buffer, identifikasjon.Identifikasjon.navnerom xml_buffer, identifikasjon.Identifikasjon.versjonId xml_buffer, oppdateringsdato xml_datetime, motorvegtype xml_buffer, vedtaksnummer xml_buffer, arkivnummer xml_buffer, senterlinje xml_geometry, lineærPosisjon{}.LineærPosisjonStrekning.lineærReferanseMetode xml_buffer, lineærPosisjon{}.LineærPosisjonStrekning.retning xml_buffer, lineærPosisjon{}.LineærPosisjonStrekning.avstandSide xml_real64, lineærPosisjon{}.LineærPosisjonStrekning.lenkesekvens.Identifikasjon.lokalId xml_buffer, lineærPosisjon{}.LineærPosisjonStrekning.lenkesekvens.Identifikasjon.navnerom xml_buffer, lineærPosisjon{}.LineærPosisjonStrekning.lenkesekvens.Identifikasjon.versjonId xml_buffer, lineærPosisjon{}.LineærPosisjonStrekning.felt xml_buffer, lineærPosisjon{}.LineærPosisjonStrekning.sideposisjon xml_buffer, lineærPosisjon{}.LineærPosisjonStrekning.høydeposisjon xml_buffer, lineærPosisjon{}.LineærPosisjonStrekning.fraPosisjon xml_real64, lineærPosisjon{}.LineærPosisjonStrekning.tilPosisjon xml_real64
    -> ListExploder
Serviceveg (reader GML_1)
    attributes: identifikasjon.Identifikasjon.lokalId xml_buffer, identifikasjon.Identifikasjon.navnerom xml_buffer, identifikasjon.Identifikasjon.versjonId xml_buffer, oppdateringsdato xml_datetime, senterlinje xml_geometry, lineærPosisjon{}.LineærPosisjonStrekning.lineærReferanseMetode xml_buffer, lineærPosisjon{}.LineærPosisjonStrekning.retning xml_buffer, lineærPosisjon{}.LineærPosisjonStrekning.avstandSide xml_real64, lineærPosisjon{}.LineærPosisjonStrekning.lenkesekvens.Identifikasjon.lokalId xml_buffer, lineærPosisjon{}.LineærPosisjonStrekning.lenkesekvens.Identifikasjon.navnerom xml_buffer, lineærPosisjon{}.LineærPosisjonStrekning.lenkesekvens.Identifikasjon.versjonId xml_buffer, lineærPosisjon{}.LineærPosisjonStrekning.felt xml_buffer, lineærPosisjon{}.LineærPosisjonStrekning.sideposisjon xml_buffer, lineærPosisjon{}.LineærPosisjonStrekning.høydeposisjon xml_buffer, lineærPosisjon{}.LineærPosisjonStrekning.fraPosisjon xml_real64, lineærPosisjon{}.LineærPosisjonStrekning.tilPosisjon xml_real64
    -> ListExploder
Svingerestriksjon (reader GML_1)
    attributes: identifikasjon.Identifikasjon.lokalId xml_buffer, identifikasjon.Identifikasjon.navnerom xml_buffer, identifikasjon.Identifikasjon.versjonId xml_buffer, oppdateringsdato xml_datetime, merknad xml_buffer, posisjon xml_geometry, svingeforbudFra.LineærPosisjonPunkt.lineærReferanseMetode xml_buffer, svingeforbudFra.LineærPosisjonPunkt.retning xml_buffer, svingeforbudFra.LineærPosisjonPunkt.avstandSide xml_real64, svingeforbudFra.LineærPosisjonPunkt.lenkesekvens.Identifikasjon.lokalId xml_buffer, svingeforbudFra.LineærPosisjonPunkt.lenkesekvens.Identifikasjon.navnerom xml_buffer, svingeforbudFra.LineærPosisjonPunkt.lenkesekvens.Identifikasjon.versjonId xml_buffer, svingeforbudFra.LineærPosisjonPunkt.felt xml_buffer, svingeforbudFra.LineærPosisjonPunkt.sideposisjon xml_buffer, svingeforbudFra.LineærPosisjonPunkt.høydeposisjon xml_buffer, svingeforbudFra.LineærPosisjonPunkt.posisjon xml_real64, svingeforbudTil.LineærPosisjonPunkt.lineærReferanseMetode xml_buffer, svingeforbudTil.LineærPosisjonPunkt.retning xml_buffer, svingeforbudTil.LineærPosisjonPunkt.avstandSide xml_real64, svingeforbudTil.LineærPosisjonPunkt.lenkesekvens.Identifikasjon.lokalId xml_buffer, svingeforbudTil.LineærPosisjonPunkt.lenkesekvens.Identifikasjon.navnerom xml_buffer, svingeforbudTil.LineærPosisjonPunkt.lenkesekvens.Identifikasjon.versjonId xml_buffer, svingeforbudTil.LineærPosisjonPunkt.felt xml_buffer, svingeforbudTil.LineærPosisjonPunkt.sideposisjon xml_buffer, svingeforbudTil.LineærPosisjonPunkt.høydeposisjon xml_buffer, svingeforbudTil.LineærPosisjonPunkt.posisjon xml_real64
    -> ListExploder
Trafikkreguleringer (reader GML_1)
    attributes: identifikasjon.Identifikasjon.lokalId xml_buffer, identifikasjon.Identifikasjon.navnerom xml_buffer, identifikasjon.Identifikasjon.versjonId xml_buffer, oppdateringsdato xml_datetime, trafikkreguleringer xml_buffer, gjeldertidsrom xml_buffer, merknad xml_buffer, senterlinje xml_geometry, lineærPosisjon{}.LineærPosisjonStrekning.lineærReferanseMetode xml_buffer, lineærPosisjon{}.LineærPosisjonStrekning.retning xml_buffer, lineærPosisjon{}.LineærPosisjonStrekning.avstandSide xml_real64, lineærPosisjon{}.LineærPosisjonStrekning.lenkesekvens.Identifikasjon.lokalId xml_buffer, lineærPosisjon{}.LineærPosisjonStrekning.lenkesekvens.Identifikasjon.navnerom xml_buffer, lineærPosisjon{}.LineærPosisjonStrekning.lenkesekvens.Identifikasjon.versjonId xml_buffer, lineærPosisjon{}.LineærPosisjonStrekning.felt xml_buffer, lineærPosisjon{}.LineærPosisjonStrekning.sideposisjon xml_buffer, lineærPosisjon{}.LineærPosisjonStrekning.høydeposisjon xml_buffer, lineærPosisjon{}.LineærPosisjonStrekning.fraPosisjon xml_real64, lineærPosisjon{}.LineærPosisjonStrekning.tilPosisjon xml_real64
    -> ListExploder
Vegsperring (reader GML_1)
    attributes: identifikasjon.Identifikasjon.lokalId xml_buffer, identifikasjon.Identifikasjon.navnerom xml_buffer, identifikasjon.Identifikasjon.versjonId xml_buffer, oppdateringsdato xml_datetime, type xml_buffer, funksjon xml_buffer, gjeldertidsrom xml_buffer, merknad xml_buffer, eier xml_buffer, posisjon xml_geometry, lineærPosisjon.LineærPosisjonPunkt.lineærReferanseMetode xml_buffer, lineærPosisjon.LineærPosisjonPunkt.retning xml_buffer, lineærPosisjon.LineærPosisjonPunkt.avstandSide xml_real64, lineærPosisjon.LineærPosisjonPunkt.lenkesekvens.Identifikasjon.lokalId xml_buffer, lineærPosisjon.LineærPosisjonPunkt.lenkesekvens.Identifikasjon.navnerom xml_buffer, lineærPosisjon.LineærPosisjonPunkt.lenkesekvens.Identifikasjon.versjonId xml_buffer, lineærPosisjon.LineærPosisjonPunkt.felt xml_buffer, lineærPosisjon.LineærPosisjonPunkt.sideposisjon xml_buffer, lineærPosisjon.LineærPosisjonPunkt.høydeposisjon xml_buffer, lineærPosisjon.LineærPosisjonPunkt.posisjon xml_real64
    -> ListExploder
VærutsattVeg (reader GML_1)
    attributes: identifikasjon.Identifikasjon.lokalId xml_buffer, identifikasjon.Identifikasjon.navnerom xml_buffer, identifikasjon.Identifikasjon.versjonId xml_buffer, oppdateringsdato xml_datetime, navn xml_buffer, høyfjellsstrekning xml_buffer, stedligBeredskap xml_buffer, snødybde xml_int64, antallStengteDøgn xml_int64, vinterstengt_FraDato xml_buffer, vinterstengt_TilDato xml_buffer, nattestengt_FraDato xml_buffer, nattestengt_TilDato xml_buffer, avgrensaVinterdriftFraDato xml_buffer, avgrensaVinterdriftTilDato xml_buffer, hovedproblem xml_buffer, gjentakelsesintervall xml_buffer, terskelverdi xml_buffer, kilde xml_buffer, tilleggsinformasjon xml_buffer, senterlinje xml_geometry, lineærPosisjon{}.LineærPosisjonStrekning.lineærReferanseMetode xml_buffer, lineærPosisjon{}.LineærPosisjonStrekning.retning xml_buffer, lineærPosisjon{}.LineærPosisjonStrekning.avstandSide xml_real64, lineærPosisjon{}.LineærPosisjonStrekning.lenkesekvens.Identifikasjon.lokalId xml_buffer, lineærPosisjon{}.LineærPosisjonStrekning.lenkesekvens.Identifikasjon.navnerom xml_buffer, lineærPosisjon{}.LineærPosisjonStrekning.lenkesekvens.Identifikasjon.versjonId xml_buffer, lineærPosisjon{}.LineærPosisjonStrekning.felt xml_buffer, lineærPosisjon{}.LineærPosisjonStrekning.sideposisjon xml_buffer, lineærPosisjon{}.LineærPosisjonStrekning.høydeposisjon xml_buffer,
      lineærPosisjon{}.LineærPosisjonStrekning.fraPosisjon xml_real64, lineærPosisjon{}.LineærPosisjonStrekning.tilPosisjon xml_real64
    -> ListExploder
